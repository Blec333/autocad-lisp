;|
APPLOAD DEPENDENCIES TO INCLUDE

  UTILITIES:
    utilityFunctions.lsp

  COMMANDS:
    
|;

(defun c:Toggle_Grille ()
;;;; TG = TOGGLE GRILLE - WILL TOGGLE NECESSARY ADJUSTMENTS TO MODEL TAPS AS GRILLES
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.CID = 818 then" writeToVBCode)
(write-line "if item.connector[3].value <> \"1 Flg In\" then" writeToVBCode)
(write-line "item.dim[\"Branch Width #1\"].value = item.dim[\"Branch Width #1\"].value + 2" writeToVBCode)
(write-line "item.dim[\"Branch Depth #1\"].value = item.dim[\"Branch Depth #1\"].value + 2" writeToVBCode)
(write-line "item.dim[\"Branch Length #1\"].value = item.dim[\"Branch Length #1\"].value - item.dim[\"Branch Length #1\"].value + 13" writeToVBCode)
(write-line "item.dim[\"Branch Extension #1\"].value = item.dim[\"Branch Extension #1\"].value - item.dim[\"Branch Extension #1\"].value + 9" writeToVBCode)
(write-line "item.damper[3].value = \"RECT DAMPER-R\"" writeToVBCode)
(write-line "item.damper[3].locked = true" writeToVBCode)
(write-line "item.update()" writeToVBCode)
(write-line "REM ==== BEGIN GRILLE FUNCTION ====" writeToVBCode)
(write-line "dim c1Num = 3" writeToVBCode)
(write-line "dim c1Name = \"1 Flg In\"" writeToVBCode)
(write-line "dim c1Grp = \"Duct - Flanged\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END GRILLE FUNCTION ====" writeToVBCode)
(write-line "elseif item.connector[3].value = \"1 Flg In\" then" writeToVBCode)
(write-line "item.dim[\"Branch Width #1\"].value = item.dim[\"Branch Width #1\"].value - 2" writeToVBCode)
(write-line "item.dim[\"Branch Depth #1\"].value = item.dim[\"Branch Depth #1\"].value - 2" writeToVBCode)
(write-line "item.dim[\"Branch Length #1\"].value = item.dim[\"Branch Length #1\"].value - item.dim[\"Branch Length #1\"].value + 6" writeToVBCode)
(write-line "item.dim[\"Branch Extension #1\"].value = item.dim[\"Branch Extension #1\"].value - item.dim[\"Branch Extension #1\"].value + 0" writeToVBCode)
(write-line "item.damper[3].value = \"NONE\"" writeToVBCode)
(write-line "item.damper[3].locked = true" writeToVBCode)
(write-line "item.update()" writeToVBCode)
(write-line "if (((wildcard(item.service, \"*1/2\"+qt+\"*\") = 1) and ((item.dim[2].value > 36 or item.dim[3].value > 36) or (item.dim[2].value > 18 and item.dim[3].value > 18)))" writeToVBCode)
(write-line "or ((wildcard(item.service, \"*1\"+qt+\"*\") = 1) and ((item.dim[2].value > 36 or item.dim[3].value > 36) or (item.dim[2].value > 18 and item.dim[3].value > 18)))" writeToVBCode)
(write-line "or ((wildcard(item.service, \"*2\"+qt+\"*\") = 1) and ((item.dim[2].value > 26 or item.dim[3].value > 26) or (item.dim[2].value > 18 and item.dim[3].value > 18)))" writeToVBCode)
(write-line "or ((wildcard(item.service, \"*3\"+qt+\"*\") = 1) and ((item.dim[2].value > 22 or item.dim[3].value > 22) or (item.dim[2].value > 18 and item.dim[3].value > 18)))" writeToVBCode)
(write-line "or ((wildcard(item.service, \"*4\"+qt+\"*\") = 1) and ((item.dim[2].value > 22 or item.dim[3].value > 22) or (item.dim[2].value > 18 and item.dim[3].value > 18)))" writeToVBCode)
(write-line "or ((wildcard(item.service, \"*6\"+qt+\"*\") = 1) and (item.dim[2].value > 0 or item.dim[3].value > 0))" writeToVBCode)
(write-line "or ((wildcard(item.service, \"*10\"+qt+\"*\") = 1) and (item.dim[2].value > 0 or item.dim[3].value > 0))) then" writeToVBCode)
(write-line "REM ==== BEGIN TDF FUNCTION ====" writeToVBCode)
(write-line "dim c1Num = 3" writeToVBCode)
(write-line "dim c1Name = \"TDF \"" writeToVBCode)
(write-line "dim c1Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END TDF FUNCTION ====" writeToVBCode)
(write-line "item.update()" writeToVBCode)
(write-line "elseif (((wildcard(item.service, \"*1/2\"+qt+\"*\") = 1) and (((item.dim[2].value <= 36 and item.dim[2].value >= 21) and item.dim[3].value <= 18) or ((item.dim[3].value <= 36 and item.dim[3].value >= 21) and item.dim[2].value <= 18)))" writeToVBCode)
(write-line "or ((wildcard(item.service, \"*1\"+qt+\"*\") = 1) and (((item.dim[2].value <= 36 and item.dim[2].value >= 21) and item.dim[3].value <= 18) or ((item.dim[3].value <= 36 and item.dim[3].value >= 21) and item.dim[2].value <= 18)))" writeToVBCode)
(write-line "or ((wildcard(item.service, \"*2\"+qt+\"*\") = 1) and (((item.dim[2].value <= 26 and item.dim[2].value >= 17) and item.dim[3].value <= 18) or ((item.dim[3].value <= 26 and item.dim[3].value >= 17) and item.dim[2].value <= 18)))" writeToVBCode)
(write-line "or ((wildcard(item.service, \"*3\"+qt+\"*\") = 1) and (((item.dim[2].value <= 22 and item.dim[2].value >= 17) and item.dim[3].value <= 18) or ((item.dim[3].value <= 22 and item.dim[3].value >= 17) and item.dim[2].value <= 18)))" writeToVBCode)
(write-line "or ((wildcard(item.service, \"*4\"+qt+\"*\") = 1) and (((item.dim[2].value <= 22 and item.dim[2].value >= 17) and item.dim[3].value <= 18) or ((item.dim[3].value <= 22 and item.dim[3].value >= 17) and item.dim[2].value <= 18)))) then" writeToVBCode)
(write-line "REM ==== BEGIN STAND S&D FUNCTION ====" writeToVBCode)
(write-line "dim c1Num = 3" writeToVBCode)
(write-line "dim c1Name = \"Stand S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END STAND S&D FUNCTION ====" writeToVBCode)
(write-line "item.update()" writeToVBCode)
(write-line "elseif (((wildcard(item.service, \"*1/2\"+qt+\"*\") = 1) and (item.dim[2].value < 21 and item.dim[3].value < 21))" writeToVBCode)
(write-line "or ((wildcard(item.service, \"*1\"+qt+\"*\") = 1) and (item.dim[2].value < 21 and item.dim[3].value < 21))" writeToVBCode)
(write-line "or ((wildcard(item.service, \"*2\"+qt+\"*\") = 1) and (item.dim[2].value < 17 and item.dim[3].value < 17))" writeToVBCode)
(write-line "or ((wildcard(item.service, \"*3\"+qt+\"*\") = 1) and (item.dim[2].value < 17 and item.dim[3].value < 17))" writeToVBCode)
(write-line "or ((wildcard(item.service, \"*4\"+qt+\"*\") = 1) and (item.dim[2].value < 17 and item.dim[3].value < 17))) then" writeToVBCode)
(write-line "REM ==== BEGIN FLAT S&D FUNCTION ====" writeToVBCode)
(write-line "dim c1Num = 3" writeToVBCode)
(write-line "dim c1Name = \"Flat S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END FLAT S&D FUNCTION ====" writeToVBCode)
(write-line "item.update()" writeToVBCode)
(write-line "end if" writeToVBCode)
(write-line "end if" writeToVBCode)
(write-line "elseif item.CID = 7 then" writeToVBCode)
(write-line "if item.connector[1].value <> \"1 Flg In\" then" writeToVBCode)
(write-line "item.dim[1].value = item.dim[1].value + 2" writeToVBCode)
(write-line "item.dim[2].value = item.dim[2].value + 2" writeToVBCode)
(write-line "item.dim[3].value = item.dim[3].numvalue - item.dim[3].numvalue + 13" writeToVBCode)
(write-line "item.dim[4].value = item.dim[4].value - item.dim[4].value + 9" writeToVBCode)
(write-line "item.damper[1].value = \"RECT DAMPER-R\"" writeToVBCode)
(write-line "item.damper[1].locked = true" writeToVBCode)
(write-line "item.update()" writeToVBCode)
(write-line "REM ==== BEGIN GRILLE FUNCTION ====" writeToVBCode)
(write-line "dim c1Num = 1" writeToVBCode)
(write-line "dim c1Name = \"1 Flg In\"" writeToVBCode)
(write-line "dim c1Grp = \"Duct - Flanged\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END GRILLE FUNCTION ====" writeToVBCode)
(write-line "elseif item.connector[1].value = \"1 Flg In\" then" writeToVBCode)
(write-line "item.dim[1].value = item.dim[1].value - 2" writeToVBCode)
(write-line "item.dim[2].value = item.dim[2].value - 2" writeToVBCode)
(write-line "item.dim[3].value = item.dim[3].numvalue - item.dim[3].numvalue + 6" writeToVBCode)
(write-line "item.dim[4].value = item.dim[4].value - item.dim[4].value + 1.5" writeToVBCode)
(write-line "item.damper[1].value = \"NONE\"" writeToVBCode)
(write-line "item.damper[1].locked = true" writeToVBCode)
(write-line "item.update()" writeToVBCode)
(write-line "if (((wildcard(item.service, \"*1/2\"+qt+\"*\") = 1) and ((item.dim[1].value > 36 or item.dim[2].value > 36) or (item.dim[1].value > 18 and item.dim[2].value > 18)))" writeToVBCode)
(write-line "or ((wildcard(item.service, \"*1\"+qt+\"*\") = 1) and ((item.dim[1].value > 36 or item.dim[2].value > 36) or (item.dim[1].value > 18 and item.dim[2].value > 18)))" writeToVBCode)
(write-line "or ((wildcard(item.service, \"*2\"+qt+\"*\") = 1) and ((item.dim[1].value > 26 or item.dim[2].value > 26) or (item.dim[1].value > 18 and item.dim[2].value > 18)))" writeToVBCode)
(write-line "or ((wildcard(item.service, \"*3\"+qt+\"*\") = 1) and ((item.dim[1].value > 22 or item.dim[2].value > 22) or (item.dim[1].value > 18 and item.dim[2].value > 18)))" writeToVBCode)
(write-line "or ((wildcard(item.service, \"*4\"+qt+\"*\") = 1) and ((item.dim[1].value > 22 or item.dim[2].value > 22) or (item.dim[1].value > 18 and item.dim[2].value > 18)))" writeToVBCode)
(write-line "or ((wildcard(item.service, \"*6\"+qt+\"*\") = 1) and (item.dim[1].value > 0 or item.dim[2].value > 0))" writeToVBCode)
(write-line "or ((wildcard(item.service, \"*10\"+qt+\"*\") = 1) and (item.dim[1].value > 0 or item.dim[2].value > 0))) then" writeToVBCode)
(write-line "REM ==== BEGIN TDF FUNCTION ====" writeToVBCode)
(write-line "dim c1Num = 1" writeToVBCode)
(write-line "dim c1Name = \"TDF \"" writeToVBCode)
(write-line "dim c1Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END TDF FUNCTION ====" writeToVBCode)
(write-line "item.update()" writeToVBCode)
(write-line "elseif (((wildcard(item.service, \"*1/2\"+qt+\"*\") = 1) and (((item.dim[1].value <= 36 and item.dim[1].value >= 21) and item.dim[2].value <= 18) or ((item.dim[2].value <= 36 and item.dim[2].value >= 21) and item.dim[1].value <= 18)))" writeToVBCode)
(write-line "or ((wildcard(item.service, \"*1\"+qt+\"*\") = 1) and (((item.dim[1].value <= 36 and item.dim[1].value >= 21) and item.dim[2].value <= 18) or ((item.dim[2].value <= 36 and item.dim[2].value >= 21) and item.dim[1].value <= 18)))" writeToVBCode)
(write-line "or ((wildcard(item.service, \"*2\"+qt+\"*\") = 1) and (((item.dim[1].value <= 26 and item.dim[1].value >= 17) and item.dim[2].value <= 18) or ((item.dim[2].value <= 26 and item.dim[2].value >= 17) and item.dim[1].value <= 18)))" writeToVBCode)
(write-line "or ((wildcard(item.service, \"*3\"+qt+\"*\") = 1) and (((item.dim[1].value <= 22 and item.dim[1].value >= 17) and item.dim[2].value <= 18) or ((item.dim[2].value <= 22 and item.dim[2].value >= 17) and item.dim[1].value <= 18)))" writeToVBCode)
(write-line "or ((wildcard(item.service, \"*4\"+qt+\"*\") = 1) and (((item.dim[1].value <= 22 and item.dim[1].value >= 17) and item.dim[2].value <= 18) or ((item.dim[2].value <= 22 and item.dim[2].value >= 17) and item.dim[1].value <= 18)))) then" writeToVBCode)
(write-line "REM ==== BEGIN STAND S&D FUNCTION ====" writeToVBCode)
(write-line "dim c1Num = 1" writeToVBCode)
(write-line "dim c1Name = \"Stand S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END STAND S&D FUNCTION ====" writeToVBCode)
(write-line "item.update()" writeToVBCode)
(write-line "elseif (((wildcard(item.service, \"*1/2\"+qt+\"*\") = 1) and (item.dim[1].value < 21 and item.dim[2].value < 21))" writeToVBCode)
(write-line "or ((wildcard(item.service, \"*1\"+qt+\"*\") = 1) and (item.dim[1].value < 21 and item.dim[2].value < 21))" writeToVBCode)
(write-line "or ((wildcard(item.service, \"*2\"+qt+\"*\") = 1) and (item.dim[1].value < 17 and item.dim[2].value < 17))" writeToVBCode)
(write-line "or ((wildcard(item.service, \"*3\"+qt+\"*\") = 1) and (item.dim[1].value < 17 and item.dim[2].value < 17))" writeToVBCode)
(write-line "or ((wildcard(item.service, \"*4\"+qt+\"*\") = 1) and (item.dim[1].value < 17 and item.dim[2].value < 17))) then" writeToVBCode)
(write-line "REM ==== BEGIN FLAT S&D FUNCTION ====" writeToVBCode)
(write-line "dim c1Num = 1" writeToVBCode)
(write-line "dim c1Name = \"Flat S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END FLAT S&D FUNCTION ====" writeToVBCode)
(write-line "item.update()" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (princ)
(END_ROUTINE));end defun
