(defun c:Execute_Script ()
  (command "executescript")
  (princ)
(END_ROUTINE));end defun
;**************************************************************************************************************************************************
(defun c:Rotate_3D ()
  (command "ROTATE3D")
  (princ)
(END_ROUTINE));end defun
;**************************************************************************************************************************************************
(defun c:Copy_Rotate ( / pt1 pt2 pt3)
  (*push-error-using-command*)
  (setq old-error *ERROR*)
  (OUTSIDE_LOOP_VARIABLES nil)
  (prompt "\nSelect items:")
  (setq sset (ssget)
        oldHighlight (getvar 'highlight))
  (setvar 'highlight 0)
  (defun CR_=1_ERROR ( msg );********************************************************
    (princ "error: ")
    (princ msg)
    (setq *ERROR* old-error
          old-error nil)
    (if oldHighlight (progn(setvar 'highlight oldHighlight)(setq oldHighlight nil)))
    (if itemsWereCopied
      (progn
        (command "erase" newItem "")
        (setq itemsWereCopied nil
              newItem nil)
      );end progn
    );end if
    (princ)
  );end defun************************************************************************
  (defun CR_2-10_ERROR ( msg );******************************************************
    (princ "error: ")
    (princ msg)
    (setq *ERROR* old-error
          old-error nil)
    (if oldHighlight (progn(setvar 'highlight oldHighlight)(setq oldHighlight nil)))
    (if UCSmadeWorld
      (progn
        (setq UCSmadeWorld nil)
        (if(not(or(= UCSname nil)(= UCSname "")))
          (command "_.UCS" "Named" "Restore" UCSname "")
          (command "_.UCS" originalUCSOrigin originalUCSx originalUCSy "")
        );end if
      );end progn
    );end if
    (if itemsWereCopied
      (progn
        (command "erase" ssLarge "")
        (setq itemsWereCopied nil
              ssLarge nil)
      );end progn
    );end if
    (princ)
  );end defun************************************************************************
  (defun CR_>1_ERROR ( msg );*******************************************************
    (if itemsWereCopied
      (progn
        (command "undo" "3")
        (setq itemsWereCopied nil)
      );end progn
    );end if
    (princ "error: ")
    (princ msg)
    (setq *ERROR* old-error
          old-error nil)
    (if oldHighlight (progn(setvar 'highlight oldHighlight)(setq oldHighlight nil)))
    
    (princ)
  );end defun************************************************************************
  (if(=(sslength sset)1)
    (progn
        (setq *ERROR* CR_=1_ERROR)
      (setq pt1 (getpoint "\nEnter Base Point:"))
      (setvar "LastPoint" pt1)
      (command ".copy" sset "" pt1 pt1)
      (setq itemsWereCopied T)
      (setq newItem (entlast))
      (command ".move" newItem "" pt1 PAUSE)
      (PROMPT "\nEnter Rotation angle:")
      (command ".rotate" newItem "" (getvar "LastPoint") PAUSE)
      (command ".REDRAW")
    );progn
    ;|
    (if(and(>(sslength sset)1)(<(sslength sset)11))
      (progn
        (setq *ERROR* CR_2-10_ERROR)
        (setq originalUCSOrigin (getvar "UCSORG")
              originalUCSx (getvar "UCSXDIR")
              originalUCSy (getvar "UCSYDIR")
              UCSname (getvar "UCSNAME"))
        (command "_.UCS" "World" "")
        (setq UCSmadeWorld T)
        (SS_BBOX sset)
        (setq ssetCompare1 (ssget "W" (list(-(car xyLL)100)(-(cadr xyLL)100))(list(+(car xyUR)100)(+(cadr xyUR)100))))
        (setq pt1 (getpoint "\nEnter Base Point:"))
        (command ".copy" sset "" pt1 pt1)
        (setq itemsWereCopied T)
        (setq ssetCompare2 (ssget "W" (list(-(car xyLL)100)(-(cadr xyLL)100))(list(+(car xyUR)100)(+(cadr xyUR)100))))
        (COMPARE_SSETS ssetCompare1 ssetCompare2)
        (command ".move" ssLarge "" pt1 pause)
        (setq pt2 (getvar 'lastpoint))
        (prompt "\nEnter Rotation angle:")
        (command ".rotate" ssLarge "" pt2 pause)
        (setq pt3 (getvar 'lastpoint))
        (setq ssLarge nil
              ssetCompare1 nil
              ssetCompare2 nil)
        (if(not(or(= UCSname nil)(= UCSname "")))
          (command "_.UCS" "Named" "Restore" UCSname "")
          (command "_.UCS" originalUCSOrigin originalUCSx originalUCSy "")
        );end if
      );progn
        (setq originalUCSOrigin (getvar "UCSORG")
              originalUCSx (getvar "UCSXDIR")
              originalUCSy (getvar "UCSYDIR")
              UCSname (getvar "UCSNAME"))
        (command "_.UCS" "World" "")
        (if(not(or(= UCSname nil)(= UCSname "")))
          (command "_.UCS" "Named" "Restore" UCSname "")
          (command "_.UCS" originalUCSOrigin originalUCSx originalUCSy "")
        );end if
      |;
      (if(>(sslength sset)1)
        (progn
          (setq *ERROR* CR_>1_ERROR)
          (setq pt1 (getpoint "\nEnter Base Point:"))
          (setvar "LastPoint" pt1)
          (command ".copy" sset "" pt1 pt1)
          (setq itemsWereCopied T)
          (command ".move" sset "" pt1 PAUSE)
          (prompt "\nEnter Rotation angle:")
          (command ".rotate" sset "" (getvar "LastPoint") PAUSE)
          (command ".REDRAW")
        );end progn
      );end if
    );end if
;  );end if
  (setvar "HighLight" oldHighlight)
  (setq *ERROR* old-error
        old-error nil
        itemsWereCopied nil)
  (princ)
(END_ROUTINE));end defun
;**************************************************************************************************************************************************
(defun c:Select_Similar_SourceFileName ()
  (prompt "\nSelect source item:")
  (setq i 0
        sset (ssget ":S"))
  (OUTSIDE_LOOP_VARIABLES nil)
  (INSIDE_LOOP_VARIABLES sset i)
  (if(and(wcmatch entGraphicID "INSERT")(wcmatch(cdr(nth 10 entlist))"*TAGS*"))
    (setq sset (ssget "_X" '((0 . "INSERT")
                            (-4 . "<OR")
                              (8 . "M-AMC-TAGS-RTRN")
                              (8 . "M-AMC-TAGS-BLCK")
                              (8 . "M-AMC-TAGS-CBST")
                              (8 . "M-AMC-TAGS-EQPM")
                              (8 . "M-AMC-TAGS-EWLD")
                              (8 . "M-AMC-TAGS-EXHA")
                              (8 . "M-AMC-TAGS-OUTA")
                              (8 . "M-AMC-TAGS-SPLY")
                              (8 . "M-AMC-TAGS-XFER")
                            (-4 . "OR>"))))
    (if(and(wcmatch entGraphicID "INSERT")(not(wcmatch(nth 10 entlist)"*TAGS*")))
      (setq sset (ssget "_X" '((0 . "INSERT"))))
      (if(wcmatch entGraphicID "MAPS_SOLID")
        (setq sset (ssget "X" (list (cons 300 ItemSourceFileName))))
      );end if
    );end if
  );end if
  (if(not(= sset nil))(command "pselect" sset "")(progn(terpri)(princ "No matches found")))
  (princ)
);end defun
;**************************************************************************************************************************************************
(defun c:Select_Similar_SourceFileName&Description ()
  (prompt "\nSelect source item:")
  (setq i 0
        sset (ssget ":S"))
  (OUTSIDE_LOOP_VARIABLES nil)
  (INSIDE_LOOP_VARIABLES sset i)
  (if(wcmatch entGraphicID "INSERT")
    (setq sset (ssget "_X" '((0 . "INSERT"))))
    (if(wcmatch entGraphicID "MAPS_SOLID")
      (setq sset (ssget "X" (list (cons -4 "<AND")(cons 300 ItemSourceFileName)(cons 300 ItemDescription)(cons -4 "AND>"))))
    );end if
  );end if
  (command "pselect" sset "")
  (princ)
);end defun
;**************************************************************************************************************************************************
(defun c:Select_Similar_ServiceType ()
  (prompt "\nSelect source item:")
  (setq i 0
        sset (ssget ":S"))
  (OUTSIDE_LOOP_VARIABLES nil)
  (if(not(= sset nil))
    (progn
      (INSIDE_LOOP_VARIABLES sset i)
      (if(wcmatch entGraphicID "INSERT")
        (setq sset (ssget "_X" '((0 . "INSERT"))))
        (if(wcmatch entGraphicID "MAPS_SOLID")
	  (progn
            (setq ServiceTypeComparison ItemServiceType
                  newset (ssadd)
                  sset (ssget "_X" '((0 . "MAPS_SOLID"))))
            (OUTSIDE_LOOP_VARIABLES sset)
            (while(< i limit)
              (INSIDE_LOOP_VARIABLES sset i)
              (if(and(not(= ItemServiceType nil))(wcmatch ItemServiceType ServiceTypeComparison))
                (ssadd ent newset)
              );end if
              (setq i (1+ i))
            );end while
          );progn
        );end if
      );end if
      (command "pselect" newset "")
      (princ)
    );progn
  );end if
);end defun
;**************************************************************************************************************************************************
(defun c:Select_Similar_Activity# ()
  (setq i 0
        Activity#Select (getstring T "n/Enter the activity # you'd like to use as a filter: ")
        sset (ssget "X" (list (cons 300 Activity#Select)))
        activitySSet (ssadd));end setq
  (OUTSIDE_LOOP_VARIABLES sset)
  (while(< i limit)
    (INSIDE_LOOP_VARIABLES sset i)
    (if(= Activity_# Activity#Select)
      (setq activitySSet (ssadd ent activitySSet))
    );end if
    (setq i (1+ i))
  );end while
  (command "pselect" activitySSet "")
  (princ)
);end defun
;**************************************************************************************************************************************************
(defun c:HangerCommand () 
   (command "hangercommand")
   (princ) 
(END_ROUTINE));end defun
;**************************************************************************************************************************************************
;multirotate is a multiple rotating utility used to rotate several
;items by one rotate factor and many reference points
;1-7-92
(defun c:Move_Rotate_Repeat ()
  (Prompt "\n\nMulti-Rotate")
  (PROMPT "\n Multi-Rotate")
  (if (not rotateref) (setq rotateref 0))
  (setq l t)
  (INITGET (+ 1 2))
  (setq temp 
	(getdist (strcat "\nEnter Rotation <" (rtos rotateref 2 2) ">: ") ) )
  (if temp (setq rotateref temp))
  (while l
    (prompt "\nSelect objects: ")
    (setq ss1 (ssget))
    (IF SS1
     (PROGN
      (INITGET (+ 1 2 4))
      (setq p1 (getpoint "\nSelect Base Point: "))
      (command "rotate" ss1 "" p1 rotateref)
     )
    )
  )
(END_ROUTINE));end defun
;**************************************************************************************************************************************************
(defun c:Move_Rotate ( / sset pt1 pt2)    ; move and rotate at the same time!
  (SETQ oldError *ERROR*)
  (defun *ERROR* (s) 
   ;YOUR COMMANDS HERE
   (SETVAR "HighLight" oldHighlight)
   (setq *ERROR* oldError)
   (SETQ oldError NIL)
   (princ)
  (END_ROUTINE));end defun err
  (SETQ oldHighlight (GETVAR "Highlight"))
  (PROMPT "\nSelect Entities to Move Rotate:")
  (SETQ sset (SSGET))
  (SETVAR "HighLight" 0)
  (SETQ Pt1 (getpoint "\nEnter Base Point:"))
  (COMMAND "move" sset "" Pt1 PAUSE)
  (PROMPT "\nEnter Rotation angle:")
  (COMMAND "ROTATE" sset "" (GETVAR "LASTPOINT") PAUSE)
  (SETVAR "HighLight" oldHighlight)
  (setq *ERROR* oldError)
  (SETQ oldError NIL)
  (princ)
(END_ROUTINE));end defun
;**************************************************************************************************************************************************
(defun c:Move_Along_Z ()
;;;; Move in the Z axis only
(setq ob (ssget)
      dis '(0.0 0.0 0.0)
      elv (getstring "Type required Z elevation <0>:")
      pt  (strcat "@0,0," elv))
(command "move" ob "" dis pt )
(princ)
(END_ROUTINE));end defun
;**************************************************************************************************************************************************
(defun c:Connection_Cycle ()
;;;; CC = CALLS UP THE CONNECTION CYCLING FILE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.connector[1].value = \"TDF \" and item.connector[2].value = \"TDF \" then" writeToVBCode)
(write-line "REM ==== BEGIN JF STEP DOWN & TDF FUNCTION ====" writeToVBCode)
(write-line "dim c1Num = 1" writeToVBCode)
(write-line "dim c1Name = \"JF 1\"+qt+\" + qt + \" DD\"" writeToVBCode)
(write-line "dim c1Grp = \"Duct - Flg Connector\"" writeToVBCode)
(write-line "dim c2Num = 2" writeToVBCode)
(write-line "dim c2Name = \"TDF \"" writeToVBCode)
(write-line "dim c2Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(write-line "REM ==== END JF STEP DOWN & TDF FUNCTION ====" writeToVBCode)
(write-line "elseif item.connector[1].value = \"JF 1\"+qt+\" + qt + \" DD\" and item.connector[2].value = \"TDF \" then" writeToVBCode)
(write-line "REM ==== BEGIN JF STEP DOWN & TDF FUNCTION ====" writeToVBCode)
(write-line "dim c1Num = 1" writeToVBCode)
(write-line "dim c1Name = \"TDF \"" writeToVBCode)
(write-line "dim c1Grp = \"Duct - Flg Connector\"" writeToVBCode)
(write-line "dim c2Num = 2" writeToVBCode)
(write-line "dim c2Name = \"JF 1\"+qt+\" + qt + \" DD\"" writeToVBCode)
(write-line "dim c2Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(write-line "REM ==== END JF STEP DOWN & TDF FUNCTION ====" writeToVBCode)
(write-line "elseif item.connector[1].value = \"TDF \" and item.connector[2].value = \"JF 1\"+qt+\" + qt + \" DD\" then" writeToVBCode)
(write-line "REM ==== BEGIN TDF FUNCTION ====" writeToVBCode)
(write-line "dim c1Num = 1" writeToVBCode)
(write-line "dim c1Name = \"TDF \"" writeToVBCode)
(write-line "dim c1Grp = \"Duct - Flg Connector\"" writeToVBCode)
(write-line "dim c2Num = 2" writeToVBCode)
(write-line "dim c2Name = \"TDF \"" writeToVBCode)
(write-line "dim c2Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END TDF FUNCTION ====" writeToVBCode)
(write-line "elseif item.connector[1].value = \"Flat S&D\" and item.connector[2].value = \"Flat S&D\" then" writeToVBCode)
(write-line "REM ==== BEGIN S&D STEP DOWN & FLAT S&D FUNCTION ====" writeToVBCode)
(write-line "dim c1Num = 1" writeToVBCode)
(write-line "dim c1Name = \"SD 1 SD\"" writeToVBCode)
(write-line "dim c1Grp = \"Duct - S&D\"" writeToVBCode)
(write-line "dim c2Num = 2" writeToVBCode)
(write-line "dim c2Name = \"Flat S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & FLAT S&D FUNCTION ====" writeToVBCode)
(write-line "elseif item.connector[1].value = \"SD 1 SD\" and item.connector[2].value = \"Flat S&D\" then" writeToVBCode)
(write-line "REM ==== BEGIN S&D STEP DOWN & FLAT S&D FUNCTION ====" writeToVBCode)
(write-line "dim c1Num = 1" writeToVBCode)
(write-line "dim c1Name = \"Flat S&D\"" writeToVBCode)
(write-line "dim c1Grp = \"Duct - S&D\"" writeToVBCode)
(write-line "dim c2Num = 2" writeToVBCode)
(write-line "dim c2Name = \"SD 1 SD\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & FLAT S&D FUNCTION ====" writeToVBCode)
(write-line "elseif item.connector[1].value = \"Flat S&D\" and item.connector[2].value = \"SD 1 SD\" then" writeToVBCode)
(write-line "REM ==== BEGIN S&D STEP DOWN & FLAT S&D FUNCTION ====" writeToVBCode)
(write-line "dim c1Num = 1" writeToVBCode)
(write-line "dim c1Name = \"Flat S&D\"" writeToVBCode)
(write-line "dim c1Grp = \"Duct - S&D\"" writeToVBCode)
(write-line "dim c2Num = 2" writeToVBCode)
(write-line "dim c2Name = \"Flat S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & FLAT S&D FUNCTION ====" writeToVBCode)
(write-line "elseif item.connector[1].value = \"Stand S&D\" and item.connector[2].value = \"Stand S&D\" then" writeToVBCode)
(write-line "REM ==== BEGIN S&D STEP DOWN & STAND S&D FUNCTION ====" writeToVBCode)
(write-line "dim c1Num = 1" writeToVBCode)
(write-line "dim c1Name = \"SD 1 SD\"" writeToVBCode)
(write-line "dim c1Grp = \"Duct - S&D\"" writeToVBCode)
(write-line "dim c2Num = 2" writeToVBCode)
(write-line "dim c2Name = \"Stand S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & STAND S&D FUNCTION ====" writeToVBCode)
(write-line "elseif item.connector[1].value = \"SD 1 SD\" and item.connector[2].value = \"Stand S&D\" then" writeToVBCode)
(write-line "REM ==== BEGIN S&D STEP DOWN & STAND S&D FUNCTION ====" writeToVBCode)
(write-line "dim c1Num = 1" writeToVBCode)
(write-line "dim c1Name = \"Stand S&D\"" writeToVBCode)
(write-line "dim c1Grp = \"Duct - S&D\"" writeToVBCode)
(write-line "dim c2Num = 2" writeToVBCode)
(write-line "dim c2Name = \"SD 1 SD\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & STAND S&D FUNCTION ====" writeToVBCode)
(write-line "elseif item.connector[1].value = \"Stand S&D\" and item.connector[2].value = \"SD 1 SD\" then" writeToVBCode)
(write-line "REM ==== BEGIN S&D STEP DOWN & STAND S&D FUNCTION ====" writeToVBCode)
(write-line "dim c1Num = 1" writeToVBCode)
(write-line "dim c1Name = \"Stand S&D\"" writeToVBCode)
(write-line "dim c1Grp = \"Duct - S&D\"" writeToVBCode)
(write-line "dim c2Num = 2" writeToVBCode)
(write-line "dim c2Name = \"Stand S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & STAND S&D FUNCTION ====" writeToVBCode)
(write-line "end if" writeToVBCode)
(write-line "i = i + 1" writeToVBCode)
(write-line "end while" writeToVBCode)
  (close writeToVBCode)
  (Executescript vbCode)
  (vl-file-delete vbCode)
  (prompt "Cycled to the next appropriate common connection option...")(princ)
  (princ)
(END_ROUTINE));end defun
;**************************************************************************************************************************************************
(defun c:Insulation_Reset ()
;;;; IR = SETS/RESETS INSULATION PER SERVICE
(OUTSIDE_LOOP_VARIABLES nil)
(write-line "requires task.selection" writeToVBCode)
(write-line "dim i = 1" writeToVBCode)
(write-line "dim qt = ASCII(34)" writeToVBCode)
(write-line "dim supplyGauge = inputbox(\"Enter SUPPLY service insulation thickness:\")" writeToVBCode)
(write-line "dim returnGauge = inputbox(\"Enter RETURN service insulation thickness:\")" writeToVBCode)
(write-line "while i <= task.selection.count" writeToVBCode)
(write-line "dim item = task.selection[i]" writeToVBCode)
(write-line "if (wildcard(item.service, \"*SUPPLY*\") = 1) and item.insulation.status <> \"INSIDE\" and (wildcard(item.description, \"*CFSD*\") = 0) and ((wildcard(supplyGauge, \"F*\") = 0) and (wildcard(supplyGauge, \"N/A\") = 0)) then" writeToVBCode)
(write-line "item.ispeclock = false" writeToVBCode)
(write-line "item.insspec = \"None\"" writeToVBCode)
(write-line "item.ispeclock = true" writeToVBCode)
(write-line "item.insulation.status = \"OUTSIDE\"" writeToVBCode)
(write-line "item.insulation.material = \"HVAC Liner: Duct Wrap\"" writeToVBCode)
(write-line "item.insulation.gauge = supplyGauge" writeToVBCode)
(write-line "item.update()" writeToVBCode)
(write-line "elseif (wildcard(item.service, \"*RETURN*\") = 1) and item.insulation.status <> \"INSIDE\" and (wildcard(item.description, \"*CFSD*\") = 0) and ((wildcard(returnGauge, \"F*\") = 0) and (wildcard(returnGauge, \"N/A\") = 0)) then" writeToVBCode)
(write-line "item.ispeclock = false" writeToVBCode)
(write-line "item.insspec = \"None\"" writeToVBCode)
(write-line "item.ispeclock = true" writeToVBCode)
(write-line "item.insulation.status = \"OUTSIDE\"" writeToVBCode)
(write-line "item.insulation.material = \"HVAC Liner: Duct Wrap\"" writeToVBCode)
(write-line "item.insulation.gauge = returnGauge" writeToVBCode)
(write-line "item.update()" writeToVBCode)
(write-line "elseif (wildcard(item.service, \"*EXHAUST*\") = 1) or (wildcard(item.description, \"*CFSD*\") = 1) or ((wildcard(item.service, \"*OUTSIDE*\") = 1) and item.insulation.status <> \"INSIDE\") then" writeToVBCode)
(write-line "item.ispeclock = false" writeToVBCode)
(write-line "item.insspec = \"None\"" writeToVBCode)
(write-line "item.ispeclock = true" writeToVBCode)
(write-line "item.insulation.status = \"OFF\"" writeToVBCode)
(write-line "item.update()" writeToVBCode)
(write-line "end if" writeToVBCode)
(write-line "i = i + 1" writeToVBCode)
(write-line "end while" writeToVBCode)
  (close writeToVBCode)
  (Executescript vbCode)
  (vl-file-delete vbCode)
  (prompt "Insulation set/reset to default.")(princ)
  (princ)
(END_ROUTINE));end defun
;**************************************************************************************************************************************************
(defun c:Insulation_Specification_NotSet ()
;;;; IR = SETS/RESETS INSULATION PER SERVICE
(OUTSIDE_LOOP_VARIABLES nil)
(setq sset (ssget "_X" '((0 . "MAPS_SOLID"))));end setq
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "item.ispeclock = false" writeToVBCode)
(write-line "item.insspec = \"None\"" writeToVBCode)
(write-line "item.ispeclock = true" writeToVBCode)
(write-line "i = i + 1" writeToVBCode)
(write-line "end while" writeToVBCode)
  (close writeToVBCode)
  (Executescript vbCode sset)
  (vl-file-delete vbCode)
  (terpri)(princ "Insulation specification set to \"Not Set\".")(princ)
  (princ)
(END_ROUTINE));end defun
;**************************************************************************************************************************************************
(defun c:Connection_Fix ()
;CF = Fixes connections based on dimension standards
  (setq i 0
        sset (ssget '((0 . "MAPS_SOLID"))));end setq
  (OUTSIDE_LOOP_VARIABLES sset)
  (while(< i limit)
    (INSIDE_LOOP_VARIABLES sset i)
    (if(= c1Spec "TDF")
      (setq newConnection1 "TDF ")
      (if(= c1Spec "Stand S&D")
        (setq newConnection1 "Stand S&D")
      (if(= c1Spec "Flat S&D")
        (setq newConnection1 "Flat S&D")
    ) ) )
      (if(= c1Spec "TDF")
        (setq connectionGroup1 "Duct - Flg Connector")
        (if(or(= c1Spec "Stand S&D")(= c1Spec "Flat S&D"))
          (setq connectionGroup1 "Duct - S&D")
      ) )
    (if(= c2Spec "TDF")
      (setq newConnection2 "TDF ")
      (if(= c2Spec "Stand S&D")
        (setq newConnection2 "Stand S&D")
      (if(= c2Spec "Flat S&D")
        (setq newConnection2 "Flat S&D")
    ) ) )
      (if(= c2Spec "TDF")
        (setq connectionGroup2 "Duct - Flg Connector")
        (if(or(= c2Spec "Stand S&D")(= c1Spec "Flat S&D"))
          (setq connectionGroup2 "Duct - S&D")
      ) )
(write-line "dim c1Num = 1" writeToVBCode)
(write-line (strcat "dim c1Name = \"" newConnection1 "\"") writeToVBCode)
(write-line (strcat "dim c1Grp = \"" connectionGroup1 "\"") writeToVBCode)
(write-line "dim c2Num = 2" writeToVBCode)
(write-line (strcat "dim c2Name = \"" newConnection2 "\"") writeToVBCode)
(write-line (strcat "dim c2Grp = \"" connectionGroup2 "\"") writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(if(and(= connectionGroup1 "Duct - Flg Connector")(= ItemCID "2"))
  (progn
    (write-line "if item.dim[6].value < 1.5 then" writeToVBCode)
    (write-line "item.dim[6].value = 1.5" writeToVBCode)
    (write-line "item.update()" writeToVBCode)
    (write-line "end if" writeToVBCode)
  );progn
);end if
(if(and(= connectionGroup2 "Duct - Flg Connector")(= ItemCID "2"))
  (progn
    (write-line "if item.dim[7].value < 1.5 then" writeToVBCode)
    (write-line "item.dim[7].value = 1.5" writeToVBCode)
    (write-line "item.update()" writeToVBCode)
    (write-line "end if" writeToVBCode)
  );progn
);end if
(write-line "item.update()" writeToVBCode)
    (close writeToVBCode)
    (executescript vbCode sset)
    (princ (strcat "Connections are now " newConnection1 " & " newConnection2))(terpri)
    (setq i (1+ i))
  );end while
  (command "pselect" sset "")
  (command "regen")
  
  ;(command "pselect" sset "")
  ;(vla-highlight vla 1)
  ;(setq thisdrawing(vla-get-activedocument(vlax-get-acad-object)))
  ;(vla-Regen thisdrawing acAllViewports)
  (princ)
(END_ROUTINE))
;|CF = Fixes connections based on dimension standards
  (setq i 0
        sset (ssget '((0 . "MAPS_SOLID"))));end setq
  (OUTSIDE_LOOP_VARIABLES sset)
  (while(< i limit)
    (INSIDE_LOOP_VARIABLES sset i)
(if(not(wcmatch itemCutType "Equipment"))
  (progn
    (if(= c1Spec "TDF")
      (setq newConnection1 "TDF ")
      (if(= c1Spec "Stand S&D")
        (setq newConnection1 "Stand S&D")
      (if(= c1Spec "Flat S&D")
        (setq newConnection1 "Flat S&D")
    ) ) )
      (if(= c1Spec "TDF")
        (setq connectionGroup1 "Duct - Flg Connector")
        (if(or(= c1Spec "Stand S&D")(= c1Spec "Flat S&D"))
          (setq connectionGroup1 "Duct - S&D")
      ) )
    (if(= c2Spec "TDF")
      (setq newConnection2 "TDF ")
      (if(= c2Spec "Stand S&D")
        (setq newConnection2 "Stand S&D")
      (if(= c2Spec "Flat S&D")
        (setq newConnection2 "Flat S&D")
    ) ) )
      (if(= c2Spec "TDF")
        (setq connectionGroup2 "Duct - Flg Connector")
        (if(or(= c2Spec "Stand S&D")(= c1Spec "Flat S&D"))
          (setq connectionGroup2 "Duct - S&D")
      ) )
(write-line "if item.connectors > 1 and (wildcard(item.connector[2].group,\"Round*\") = 1) and item.cuttype <> \"Equipment\" and item.CID <> 8 then" writeToVBCode)
(write-line "if item.CID = 40 then" writeToVBCode)
(write-line "dim c1Num = 1" writeToVBCode)
(write-line "dim c1Name = \"Raw\"" writeToVBCode)
(write-line "dim c1Grp = \"Round Duct\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "dim c2Num = 2" writeToVBCode)
(write-line "dim c2Name = \"Raw\"" writeToVBCode)
(write-line "dim c2Grp = \"Round Duct\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c2Num].value = c1Name" writeToVBCode)
(write-line "item.connector[c2Num].locked = true" writeToVBCode)
(write-line "if item.connector[c2Num].group <> c1Grp then" writeToVBCode)
(write-line "connFind(c2Num,c2Grp,c2Name)" writeToVBCode)
(write-line "end if" writeToVBCode)
(write-line "end if" writeToVBCode)
(write-line "elseif item.connectors > 1 and (wildcard(item.connector[2].group,\"Round*\") = 0) and item.cuttype <> \"Equipment\" and item.CID <> 8 then" writeToVBCode)
(write-line "dim c1Num = 1" writeToVBCode)
(write-line (strcat "dim c1Name = \"" newConnection1 "\"") writeToVBCode)
(write-line (strcat "dim c1Grp = \"" connectionGroup1 "\"") writeToVBCode)
(write-line "dim c2Num = 2" writeToVBCode)
(write-line (strcat "dim c2Name = \"" newConnection2 "\"") writeToVBCode)
(write-line (strcat "dim c2Grp = \"" connectionGroup2 "\"") writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(if(and(= connectionGroup1 "Duct - Flg Connector")(= ItemCID "2"))
  (progn
    (write-line "if item.dim[6].value < 1.5 then" writeToVBCode)
    (write-line "item.dim[6].value = 1.5" writeToVBCode)
    (write-line "item.update()" writeToVBCode)
    (write-line "end if" writeToVBCode)
  );progn
);end if
(if(and(= connectionGroup2 "Duct - Flg Connector")(= ItemCID "2"))
  (progn
    (write-line "if item.dim[7].value < 1.5 then" writeToVBCode)
    (write-line "item.dim[7].value = 1.5" writeToVBCode)
    (write-line "item.update()" writeToVBCode)
    (write-line "end if" writeToVBCode)
  );progn
);end if
(write-line "item.update()" writeToVBCode)
(write-line "end if" writeToVBCode)
    (close writeToVBCode)
    (executescript vbCode ent)
    (setq writeToVBCode nil
          writeToVBCode (open vbCode "w"))
    ;(princ (strcat "Connections are now " newConnection1 " & " newConnection2))(terpri)
    );progn
  );end if
    (setq i (1+ i))
  );end while
  (command "pselect" sset "")
  (command "regen")
  ;(command "pselect" sset "")
  ;(vla-highlight vla 1)
  ;(setq thisdrawing(vla-get-activedocument(vlax-get-acad-object)))
  ;(vla-Regen thisdrawing acAllViewports)
  (princ)
(END_ROUTINE));end defun
|;
;**************************************************************************************************************************************************
(defun c:Damper_Cycle ()
;;;; DC = CYCLES DAMPER OPTIONS WHERE APPROPRIATE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnTapSqRdDamper ()" writeToVBCode)
(write-line "dim item = task.selection[i]" writeToVBCode)
(write-line "if (((item.CID = 345 or item.CID = 751 or item.CID = 51 or item.CID = 875) and item.dim[2].value <= 12) or (item.CID = 16 and item.dim[1].value <= 12) or (item.CID = 8 and item.dim[3].value <= 12)) then" writeToVBCode)
(write-line "if item.dampers = 1 then" writeToVBCode)
(write-line "if item.CID = 345 and item.damper[1].value = \"NONE\" then" writeToVBCode)
(write-line "if item.dim[9].locked = false then" writeToVBCode)
(write-line "item.dim[9].value = 6" writeToVBCode)
(write-line "end if" writeToVBCode)
(write-line "item.damper[1].value = \"KS7L-l\"" writeToVBCode)
(write-line "item.damper[1].locked = true" writeToVBCode)
(write-line "item.update()" writeToVBCode)
(write-line "elseif item.CID = 16 and item.damper[1].value = \"NONE\" then" writeToVBCode)
(write-line "if item.dim[2].locked = false then" writeToVBCode)
(write-line "item.dim[2].value = 6" writeToVBCode)
(write-line "end if" writeToVBCode)
(write-line "item.damper[1].value = \"KS7L-l\"" writeToVBCode)
(write-line "item.damper[1].locked = true" writeToVBCode)
(write-line "item.update()" writeToVBCode)
(write-line "elseif item.CID = 8 and item.damper[1].value = \"NONE\" then" writeToVBCode)
(write-line "if item.dim[8].locked = false then" writeToVBCode)
(write-line "item.dim[8].value = 6" writeToVBCode)
(write-line "end if" writeToVBCode)
(write-line "item.damper[1].value = \"KS7L-l\"" writeToVBCode)
(write-line "item.damper[1].locked = true" writeToVBCode)
(write-line "item.update()" writeToVBCode)
(write-line "end if" writeToVBCode)
(write-line "elseif item.dampers = 2 then" writeToVBCode)
(write-line "if item.CID = 51 and item.damper[2].value = \"NONE\" then" writeToVBCode)
(write-line "if item.dim[2].value >= 4 and item.dim[2].value <= 6 then" writeToVBCode)
(write-line "if item.dim[3].locked = false then" writeToVBCode)
(write-line "item.dim[3].value = 6" writeToVBCode)
(write-line "item.update()" writeToVBCode)
(write-line "end if" writeToVBCode)
(write-line "elseif item.dim[2].value >= 7 and item.dim[2].value <= 10 then" writeToVBCode)
(write-line "if item.dim[3].locked = false then" writeToVBCode)
(write-line "item.dim[3].value = 10" writeToVBCode)
(write-line "item.update()" writeToVBCode)
(write-line "end if" writeToVBCode)
(write-line "elseif item.dim[2].value >= 11 and item.dim[2].value <= 12 then" writeToVBCode)
(write-line "if item.dim[3].locked = false then" writeToVBCode)
(write-line "item.dim[3].value = 12" writeToVBCode)
(write-line "item.update()" writeToVBCode)
(write-line "end if" writeToVBCode)
(write-line "end if" writeToVBCode)
(write-line "item.damper[2].value = \"KS7L-l\"" writeToVBCode)
(write-line "item.damper[2].locked = true" writeToVBCode)
(write-line "item.update()" writeToVBCode)
(write-line "end if" writeToVBCode)
(write-line "elseif item.dampers = 3 then" writeToVBCode)
(write-line "if item.CID = 875 and item.damper[3].value = \"NONE\" then" writeToVBCode)
(write-line "if item.description = \"*saddle*\" then" writeToVBCode)
(write-line "if item.dim[3].locked = false then" writeToVBCode)
(write-line "item.dim[3].value = 6" writeToVBCode)
(write-line "end if" writeToVBCode)
(write-line "elseif item.description <> \"*saddle*\" then" writeToVBCode)
(write-line "if item.dim[3].locked = false then" writeToVBCode)
(write-line "item.dim[3].value = 15" writeToVBCode)
(write-line "end if" writeToVBCode)
(write-line "end if" writeToVBCode)
(write-line "item.damper[3].value = \"KS7L-l\"" writeToVBCode)
(write-line "item.damper[3].locked = true" writeToVBCode)
(write-line "item.update()" writeToVBCode)
(write-line "elseif item.CID = 751 and item.damper[3].value = \"NONE\" then" writeToVBCode)
(write-line "if item.dim[5].locked = false then" writeToVBCode)
(write-line "item.dim[5].value = 6" writeToVBCode)
(write-line "end if" writeToVBCode)
(write-line "item.damper[3].value = \"KS7L-l\"" writeToVBCode)
(write-line "item.damper[3].locked = true" writeToVBCode)
(write-line "item.update()" writeToVBCode)
(write-line "end if" writeToVBCode)
(write-line "item.update()" writeToVBCode)
(write-line "end if" writeToVBCode)
(write-line "elseif (((item.CID = 345 or item.CID = 751 or item.CID = 51 or item.CID = 875) and item.dim[2].value > 12) or (item.CID = 16 and item.dim[1].value > 12) or (item.CID = 8 and item.dim[3].value > 12)) then" writeToVBCode)
(write-line "if item.dampers = 1 then" writeToVBCode)
(write-line "if item.CID = 345 and item.damper[1].value = \"NONE\" then" writeToVBCode)
(write-line "if item.dim[9].locked = false then" writeToVBCode)
(write-line "item.dim[9].value = 6" writeToVBCode)
(write-line "end if" writeToVBCode)
(write-line "item.damper[1].value = \"3/8\"+qt+\" ROD-L\"" writeToVBCode)
(write-line "item.damper[1].locked = true" writeToVBCode)
(write-line "elseif item.CID = 16 and item.damper[1].value = \"NONE\" then" writeToVBCode)
(write-line "if item.dim[2].locked = false then" writeToVBCode)
(write-line "item.dim[2].value = 6" writeToVBCode)
(write-line "end if" writeToVBCode)
(write-line "item.damper[1].value = \"3/8\"+qt+\" ROD-L\"" writeToVBCode)
(write-line "item.damper[1].locked = true" writeToVBCode)
(write-line "item.update()" writeToVBCode)
(write-line "elseif item.CID = 8 and item.damper[1].value = \"NONE\" then" writeToVBCode)
(write-line "if item.dim[8].locked = false then" writeToVBCode)
(write-line "item.dim[8].value = 6" writeToVBCode)
(write-line "end if" writeToVBCode)
(write-line "item.damper[1].value = \"3/8\"+qt+\" ROD-L\"" writeToVBCode)
(write-line "item.damper[1].locked = true" writeToVBCode)
(write-line "item.update()" writeToVBCode)
(write-line "end if" writeToVBCode)
(write-line "elseif item.dampers = 2 then" writeToVBCode)
(write-line "if item.CID = 51 and item.damper[2].value = \"NONE\" then" writeToVBCode)
(write-line "if item.dim[2].value > 12 and item.dim[2].value <= 14 then" writeToVBCode)
(write-line "if item.dim[3].locked = false then" writeToVBCode)
(write-line "item.dim[3].value = 12" writeToVBCode)
(write-line "item.update()" writeToVBCode)
(write-line "end if" writeToVBCode)
(write-line "elseif item.dim[2].value >= 16 and item.dim[2].value <= 18 then" writeToVBCode)
(write-line "if item.dim[3].locked = false then" writeToVBCode)
(write-line "item.dim[3].value = 15" writeToVBCode)
(write-line "item.update()" writeToVBCode)
(write-line "end if" writeToVBCode)
(write-line "elseif item.dim[2].value >= 20 then" writeToVBCode)
(write-line "if item.dim[3].locked = false then" writeToVBCode)
(write-line "item.dim[3].value = 20" writeToVBCode)
(write-line "item.update()" writeToVBCode)
(write-line "end if" writeToVBCode)
(write-line "end if" writeToVBCode)
(write-line "item.damper[2].value = \"3/8\"+qt+\" ROD-L\"" writeToVBCode)
(write-line "item.damper[2].locked = true" writeToVBCode)
(write-line "end if" writeToVBCode)
(write-line "elseif item.dampers = 3 then" writeToVBCode)
(write-line "if item.CID = 875 and item.damper[3].value = \"NONE\" then" writeToVBCode)
(write-line "if item.description = \"*saddle*\" then" writeToVBCode)
(write-line "if item.dim[3].locked = false then" writeToVBCode)
(write-line "item.dim[3].value = 6" writeToVBCode)
(write-line "end if" writeToVBCode)
(write-line "elseif item.description <> \"*saddle*\" then" writeToVBCode)
(write-line "if item.dim[3].locked = false then" writeToVBCode)
(write-line "item.dim[3].value = 15" writeToVBCode)
(write-line "end if" writeToVBCode)
(write-line "end if" writeToVBCode)
(write-line "item.damper[3].value = \"3/8\"+qt+\" ROD-L\"" writeToVBCode)
(write-line "item.damper[3].locked = true" writeToVBCode)
(write-line "item.update()" writeToVBCode)
(write-line "elseif item.CID = 751 and item.damper[3].value = \"NONE\" then" writeToVBCode)
(write-line "if item.dim[9].locked = false then" writeToVBCode)
(write-line "item.dim[5].value = 6" writeToVBCode)
(write-line "end if" writeToVBCode)
(write-line "item.damper[3].value = \"3/8\"+qt+\" ROD-L\"" writeToVBCode)
(write-line "item.damper[3].locked = true" writeToVBCode)
(write-line "item.update()" writeToVBCode)
(write-line "end if" writeToVBCode)
(write-line "item.update()" writeToVBCode)
(write-line "end if" writeToVBCode)
(write-line "item.update()" writeToVBCode)
(write-line "end if" writeToVBCode)
(write-line "end function" writeToVBCode)
(write-line "function turnOffTapSqRdDamper ()" writeToVBCode)
(write-line "dim item = task.selection[i]" writeToVBCode)
(write-line "if item.dampers = 1 then" writeToVBCode)
(write-line "if item.CID = 345 and item.damper[1].value <> \"NONE\" then" writeToVBCode)
(write-line "if item.dim[9].locked = false then" writeToVBCode)
(write-line "item.dim[9].value = 0" writeToVBCode)
(write-line "end if" writeToVBCode)
(write-line "item.damper[1].value = \"NONE\"" writeToVBCode)
(write-line "item.damper[1].locked = true" writeToVBCode)
(write-line "item.update()" writeToVBCode)
(write-line "elseif item.CID = 16 and item.damper[1].value <> \"NONE\" then" writeToVBCode)
(write-line "if item.dim[2].locked = false then" writeToVBCode)
(write-line "item.dim[2].value = 6" writeToVBCode)
(write-line "end if" writeToVBCode)
(write-line "item.damper[1].value = \"NONE\"" writeToVBCode)
(write-line "item.damper[1].locked = true" writeToVBCode)
(write-line "item.update()" writeToVBCode)
(write-line "elseif item.CID = 8 and item.damper[1].value <> \"NONE\" then" writeToVBCode)
(write-line "if item.dim[8].locked = false then" writeToVBCode)
(write-line "item.dim[8].value = 3" writeToVBCode)
(write-line "end if" writeToVBCode)
(write-line "item.damper[1].value = \"NONE\"" writeToVBCode)
(write-line "item.damper[1].locked = true" writeToVBCode)
(write-line "item.update()" writeToVBCode)
(write-line "end if" writeToVBCode)
(write-line "elseif item.dampers = 2 then" writeToVBCode)
(write-line "if item.CID = 51 and item.damper[2].value <> \"NONE\" then" writeToVBCode)
(write-line "if item.dim[3].locked = false then" writeToVBCode)
(write-line "item.dim[3].value = 3.75" writeToVBCode)
(write-line "end if" writeToVBCode)
(write-line "item.damper[2].value = \"NONE\"" writeToVBCode)
(write-line "item.damper[2].locked = true" writeToVBCode)
(write-line "item.update()" writeToVBCode)
(write-line "end if" writeToVBCode)
(write-line "elseif item.dampers = 3 then" writeToVBCode)
(write-line "if item.CID = 875 and item.damper[3].value <> \"NONE\" then" writeToVBCode)
(write-line "if item.dim[3].locked = false then" writeToVBCode)
(write-line "item.dim[3].value = 6" writeToVBCode)
(write-line "end if" writeToVBCode)
(write-line "item.damper[3].value = \"NONE\"" writeToVBCode)
(write-line "item.damper[3].locked = true" writeToVBCode)
(write-line "item.update()" writeToVBCode)
(write-line "elseif item.CID = 751 and item.damper[3].value <> \"NONE\" then" writeToVBCode)
(write-line "if item.dim[5].locked = false then" writeToVBCode)
(write-line "item.dim[5].value = 0" writeToVBCode)
(write-line "end if" writeToVBCode)
(write-line "item.damper[3].value = \"NONE\"" writeToVBCode)
(write-line "item.damper[3].locked = true" writeToVBCode)
(write-line "item.update()" writeToVBCode)
(write-line "end if" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD2 ()" writeToVBCode)
(write-line "dim item = task.selection[i]" writeToVBCode)
(write-line "if (((item.CID = 53 or item.CID = 54 or item.CID = 345 or item.CID = 751 or item.CID = 51 or item.CID = 875) and item.dim[2].value <= 12) or ((item.CID = 807 or item.CID = 812 or item.CID = 16) and item.dim[1].value <= 12) or (item.CID = 8 and item.dim[3].value <= 12)) then" writeToVBCode)
(write-line "if item.CID = 53 or item.CID = 54 then" writeToVBCode)
(write-line "item.dim[5].value = 6" writeToVBCode)
(write-line "item.update()" writeToVBCode)
(write-line "elseif item.CID = 807 or item.CID = 812 then" writeToVBCode)
(write-line "item.dim[4].value = 6" writeToVBCode)
(write-line "item.update()" writeToVBCode)
(write-line "end if" writeToVBCode)
(write-line "item.damper[2].value = \"KS7L-l\"" writeToVBCode)
(write-line "item.damper[2].locked = true" writeToVBCode)
(write-line "item.update()" writeToVBCode)
(write-line "elseif (((item.CID = 53 or item.CID = 54) and item.dim[2].value > 12) or ((item.CID = 807 or item.CID = 812) and item.dim[1].value > 12) or (item.CID = 8 and item.dim[3].value > 12)) then" writeToVBCode)
(write-line "if item.CID = 53 or item.CID = 54 then" writeToVBCode)
(write-line "item.dim[5].value = 6" writeToVBCode)
(write-line "item.update()" writeToVBCode)
(write-line "elseif item.CID = 807 or item.CID = 812 then" writeToVBCode)
(write-line "item.dim[4].value = 6" writeToVBCode)
(write-line "item.update()" writeToVBCode)
(write-line "end if" writeToVBCode)
(write-line "item.damper[2].value = \"3/8\"+qt+\" ROD-L\"" writeToVBCode)
(write-line "item.damper[2].locked = true" writeToVBCode)
(write-line "item.update()" writeToVBCode)
(write-line "end if" writeToVBCode)
(write-line "end function" writeToVBCode)
(write-line "function turnOffD2 ()" writeToVBCode)
(write-line "dim item = task.selection[i]" writeToVBCode)
(write-line "if item.CID = 53 or item.CID = 54 then" writeToVBCode)
(write-line "item.dim[5].value = 0" writeToVBCode)
(write-line "item.damper[2].value = \"NONE\"" writeToVBCode)
(write-line "item.damper[2].locked = true" writeToVBCode)
(write-line "item.update()" writeToVBCode)
(write-line "elseif item.CID = 807 or item.CID = 812 then" writeToVBCode)
(write-line "item.dim[4].value = 1" writeToVBCode)
(write-line "item.damper[2].value = \"NONE\"" writeToVBCode)
(write-line "item.damper[2].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD3 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.damper[3].value = \"KS7L-l\"" writeToVBCode)
(write-line "item.damper[3].locked = true" writeToVBCode)
(write-line "item.update()" writeToVBCode)
(write-line "elseif item.CID = 807 or item.CID = 812 then" writeToVBCode)
(write-line "item.damper[3].value = \"KS7L-l\"" writeToVBCode)
(write-line "item.damper[3].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.damper[3].value = \"3/8\"+qt+\" ROD-L\"" writeToVBCode)
(write-line "item.damper[3].locked = true" writeToVBCode)
(write-line "item.update()" writeToVBCode)
(write-line "elseif item.CID = 807 or item.CID = 812 then" writeToVBCode)
(write-line "item.damper[3].value = \"3/8\"+qt+\" ROD-L\"" writeToVBCode)
(write-line "item.damper[3].locked = true" writeToVBCode)
(write-line "item.update()" writeToVBCode)
(write-line "end if" writeToVBCode)
(write-line "item.update()" writeToVBCode)
(write-line "end if" writeToVBCode)
(write-line "end function" writeToVBCode)
(write-line "function turnOffD3 ()" writeToVBCode)
(write-line "dim item = task.selection[i]" writeToVBCode)
(write-line "if item.CID = 53 or item.CID = 54 or item.CID = 807 or item.CID = 812 then" writeToVBCode)
(write-line "item.damper[3].value = \"NONE\"" writeToVBCode)
(write-line "item.damper[3].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD4 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.damper[4].value = \"KS7L-l\"" writeToVBCode)
(write-line "item.damper[4].locked = true" writeToVBCode)
(write-line "item.update()" writeToVBCode)
(write-line "elseif item.CID = 807 or item.CID = 812 then" writeToVBCode)
(write-line "item.damper[4].value = \"KS7L-l\"" writeToVBCode)
(write-line "item.damper[4].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.damper[4].value = \"3/8\"+qt+\" ROD-L\"" writeToVBCode)
(write-line "item.damper[4].locked = true" writeToVBCode)
(write-line "item.update()" writeToVBCode)
(write-line "elseif item.CID = 807 or item.CID = 812 then" writeToVBCode)
(write-line "item.damper[4].value = \"3/8\"+qt+\" ROD-L\"" writeToVBCode)
(write-line "item.damper[4].locked = true" writeToVBCode)
(write-line "item.update()" writeToVBCode)
(write-line "end if" writeToVBCode)
(write-line "item.update()" writeToVBCode)
(write-line "end if" writeToVBCode)
(write-line "end function" writeToVBCode)
(write-line "function turnOffD4 ()" writeToVBCode)
(write-line "dim item = task.selection[i]" writeToVBCode)
(write-line "if item.CID = 53 or item.CID = 54 or item.CID = 807 or item.CID = 812 then" writeToVBCode)
(write-line "item.damper[4].value = \"NONE\"" writeToVBCode)
(write-line "item.damper[4].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD2D3 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.dim[5].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.update()" writeToVBCode)
(write-line "elseif item.CID = 807 or item.CID = 812 then" writeToVBCode)
(write-line "item.dim[4].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.dim[5].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.update()" writeToVBCode)
(write-line "elseif item.CID = 807 or item.CID = 812 then" writeToVBCode)
(write-line "item.dim[4].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.update()" writeToVBCode)
(write-line "end if" writeToVBCode)
(write-line "item.update()" writeToVBCode)
(write-line "end if" writeToVBCode)
(write-line "end function" writeToVBCode)
(write-line "function turnOffD2D3 ()" writeToVBCode)
(write-line "dim item = task.selection[i]" writeToVBCode)
(write-line "if item.CID = 53 or item.CID = 54 then" writeToVBCode)
(write-line "item.dim[5].value = 0" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.update()" writeToVBCode)
(write-line "elseif item.CID = 807 or item.CID = 812 then" writeToVBCode)
(write-line "item.dim[4].value = 1" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD2D3D4 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.dim[5].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.damper[4].value = \"KS7L-l\"" writeToVBCode)
(write-line "item.damper[4].locked = true" writeToVBCode)
(write-line "item.update()" writeToVBCode)
(write-line "elseif item.CID = 807 or item.CID = 812 then" writeToVBCode)
(write-line "item.dim[4].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.damper[4].value = \"KS7L-l\"" writeToVBCode)
(write-line "item.damper[4].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.dim[5].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.damper[4].value = \"3/8\"+qt+\" ROD-L\"" writeToVBCode)
(write-line "item.damper[4].locked = true" writeToVBCode)
(write-line "item.update()" writeToVBCode)
(write-line "elseif item.CID = 807 or item.CID = 812 then" writeToVBCode)
(write-line "item.dim[4].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.damper[4].value = \"3/8\"+qt+\" ROD-L\"" writeToVBCode)
(write-line "item.damper[4].locked = true" writeToVBCode)
(write-line "item.update()" writeToVBCode)
(write-line "end if" writeToVBCode)
(write-line "item.update()" writeToVBCode)
(write-line "end if" writeToVBCode)
(write-line "end function" writeToVBCode)
(write-line "function turnOffD2D3D4 ()" writeToVBCode)
(write-line "dim item = task.selection[i]" writeToVBCode)
(write-line "if item.CID = 53 or item.CID = 54 then" writeToVBCode)
(write-line "item.dim[5].value = 0" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.damper[4].value = \"NONE\"" writeToVBCode)
(write-line "item.damper[4].locked = true" writeToVBCode)
(write-line "item.update()" writeToVBCode)
(write-line "elseif item.CID = 807 or item.CID = 812 then" writeToVBCode)
(write-line "item.dim[4].value = 1" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.damper[4].value = \"NONE\"" writeToVBCode)
(write-line "item.damper[4].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "if item.CID = 51 or item.CID = 751 or item.CID = 875 or item.CID = 345 or item.CID = 16 or item.CID = 8 then" writeToVBCode)
(write-line "if item.dampers = 1 then" writeToVBCode)
(write-line "if ((item.CID = 345 or item.CID = 16 or item.CID = 8) and item.damper[1].value = \"NONE\") then" writeToVBCode)
(write-line "turnOnTapSqRdDamper ()" writeToVBCode)
(write-line "elseif ((item.CID = 345 or item.CID = 16 or item.CID = 8) and item.damper[1].value <> \"NONE\") then" writeToVBCode)
(write-line "turnOffTapSqRdDamper ()" writeToVBCode)
(write-line "end if" writeToVBCode)
(write-line "elseif item.dampers = 2 then" writeToVBCode)
(write-line "if item.CID = 51 and item.damper[2].value = \"NONE\" then" writeToVBCode)
(write-line "turnOnTapSqRdDamper ()" writeToVBCode)
(write-line "elseif item.CID = 51 and item.damper[2].value <> \"NONE\" then" writeToVBCode)
(write-line "turnOffTapSqRdDamper ()" writeToVBCode)
(write-line "end if" writeToVBCode)
(write-line "elseif item.dampers = 3 then" writeToVBCode)
(write-line "if ((item.CID = 751 or item.CID = 875) and item.damper[3].value = \"NONE\") then" writeToVBCode)
(write-line "turnOnTapSqRdDamper ()" writeToVBCode)
(write-line "elseif ((item.CID = 751 or item.CID = 875) and item.damper[3].value <> \"NONE\") then" writeToVBCode)
(write-line "turnOffTapSqRdDamper ()" writeToVBCode)
(write-line "end if" writeToVBCode)
(write-line "end if" writeToVBCode)
(write-line "elseif item.CID <> 51 and item.CID <> 751 and item.CID <> 875 and item.CID <> 345 and item.CID <> 16 and item.CID <> 8 then" writeToVBCode)
(write-line "if item.dampers = 1 then" writeToVBCode)
(write-line "if item.damper[1].value = \"NONE\" then" writeToVBCode)
(write-line "turnOnD1 ()" writeToVBCode)
(write-line "elseif item.damper[1].value <> \"NONE\" then" writeToVBCode)
(write-line "turnOffD1 ()" writeToVBCode)
(write-line "end if" writeToVBCode)
(write-line "elseif item.dampers = 2 then" writeToVBCode)
(write-line "if item.damper[2].value = \"NONE\" then" writeToVBCode)
(write-line "turnOnD2 ()" writeToVBCode)
(write-line "elseif item.damper[2].value <> \"NONE\" then" writeToVBCode)
(write-line "turnOffD2 ()" writeToVBCode)
(write-line "end if" writeToVBCode)
(write-line "elseif item.dampers = 3 then" writeToVBCode)
(write-line "if item.damper[2].value = \"NONE\" and item.damper[3].value = \"NONE\" then" writeToVBCode)
(write-line "turnOnD3 ()" writeToVBCode)
(write-line "elseif item.damper[2].value = \"NONE\" and item.damper[3].value <> \"NONE\" then" writeToVBCode)
(write-line "turnOffD3 ()" writeToVBCode)
(write-line "turnOnD2 ()" writeToVBCode)
(write-line "elseif item.damper[2].value <> \"NONE\" and item.damper[3].value = \"NONE\" then" writeToVBCode)
(write-line "turnOnD2D3 ()" writeToVBCode)
(write-line "elseif item.damper[2].value <> \"NONE\" and item.damper[3].value <> \"NONE\" then" writeToVBCode)
(write-line "turnOffD2D3 ()" writeToVBCode)
(write-line "end if" writeToVBCode)
(write-line "elseif item.dampers = 4 then" writeToVBCode)
(write-line "if item.damper[2].value = \"NONE\" and item.damper[3].value = \"NONE\" and item.damper[4].value = \"NONE\" then" writeToVBCode)
(write-line "turnOnD3 ()" writeToVBCode)
(write-line "elseif item.damper[2].value = \"NONE\" and item.damper[3].value <> \"NONE\" and item.damper[4].value = \"NONE\" then" writeToVBCode)
(write-line "turnOffD3 ()" writeToVBCode)
(write-line "turnOnD4 ()" writeToVBCode)
(write-line "elseif item.damper[2].value = \"NONE\" and item.damper[3].value = \"NONE\" and item.damper[4].value <> \"NONE\" then" writeToVBCode)
(write-line "turnOffD4 ()" writeToVBCode)
(write-line "turnOnD2 ()" writeToVBCode)
(write-line "elseif item.damper[2].value <> \"NONE\" and item.damper[3].value = \"NONE\" and item.damper[4].value = \"NONE\" then" writeToVBCode)
(write-line "turnOnD3 ()" writeToVBCode)
(write-line "elseif item.damper[2].value <> \"NONE\" and item.damper[3].value <> \"NONE\" and item.damper[4].value = \"NONE\" then" writeToVBCode)
(write-line "turnOffD3 ()" writeToVBCode)
(write-line "turnOnD4 ()" writeToVBCode)
(write-line "elseif item.damper[2].value <> \"NONE\" and item.damper[3].value = \"NONE\" and item.damper[4].value <> \"NONE\" then" writeToVBCode)
(write-line "turnOffD2 ()" writeToVBCode)
(write-line "turnOnD3 ()" writeToVBCode)
(write-line "elseif item.damper[2].value = \"NONE\" and item.damper[3].value <> \"NONE\" and item.damper[4].value <> \"NONE\" then" writeToVBCode)
(write-line "turnOnD2 ()" writeToVBCode)
(write-line "elseif item.damper[2].value <> \"NONE\" and item.damper[3].value <> \"NONE\" and item.damper[4].value <> \"NONE\" then" writeToVBCode)
(write-line "turnOffD2D3D4 ()" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (prompt "Cycling through volume damper locations...")(princ)
  (princ)
(END_ROUTINE));end defun
;**************************************************************************************************************************************************
(defun c:Hanger_Stretch_to_Section ()
  ;;;; HS = HANGER STRETCH
(setq hangers (ssget '((0 . "MAPS_SOLID"))))
(OUTSIDE_LOOP_VARIABLES nil)
(write-line "dim i = 1" writeToVBCode)
(write-line "dim qt = ASCII(34)" writeToVBCode)
(write-line "select item.CID" writeToVBCode)
(write-line "case 838,902" writeToVBCode)
(write-line "rem Floor Supports =====================================================================================================" writeToVBCode)
(write-line "if (wildcard(item.filename,\"double rectangular floor mount\") = 1) and (wildcard(item.option[1].value, \"Double Profile Bearer 2\") = 1) then" writeToVBCode)
(write-line "dim depth = item.dim[2].value" writeToVBCode)
(write-line "dim bottomElevation = item.endlocation(1,\"btm\")" writeToVBCode)
(write-line "dim floorLevel = item.level(\"floor\")" writeToVBCode)
(write-line "dim legLength = ((bottomElevation-floorLevel)+depth)" writeToVBCode)
(write-line "item.option[21].value = 0.5" writeToVBCode)
(write-line "item.dim[6].value = (0 - legLength)" writeToVBCode)
(write-line "item.dim[7].value = (0 - depth)" writeToVBCode)
(write-line "elseif (wildcard(item.filename,\"single rectangular floor mount\") = 1) and (wildcard(item.option[1].value, \"Profiled Bearer\") = 1) then" writeToVBCode)
(write-line "dim depth = item.dim[2].value" writeToVBCode)
(write-line "dim bottomElevation = item.endlocation(1,\"btm\")" writeToVBCode)
(write-line "dim floorLevel = item.level(\"floor\")" writeToVBCode)
(write-line "dim legLength = ((bottomElevation-floorLevel)+depth)" writeToVBCode)
(write-line "item.option[21].value = 0 - 0.5" writeToVBCode)
(write-line "item.dim[6].value = (0 - legLength)" writeToVBCode)
(write-line "item.dim[7].value = (0 - 6)" writeToVBCode)
(write-line "elseif (wildcard(item.filename,\"*rectangular floor mount\") = 1) and (wildcard(item.option[1].value, \"Flat Strap Hanger\") = 1) then" writeToVBCode)
(write-line "dim depth = item.dim[2].value" writeToVBCode)
(write-line "dim bottomElevation = item.endlocation(1,\"btm\")" writeToVBCode)
(write-line "dim floorLevel = item.level(\"floor\")" writeToVBCode)
(write-line "dim legLength = (bottomElevation-floorLevel)" writeToVBCode)
(write-line "item.option[12].value = 0.5" writeToVBCode)
(write-line "item.dim[3].value = (0 - legLength)" writeToVBCode)
(write-line "elseif (wildcard(item.filename,\"*round floor mount\") = 1) then" writeToVBCode)
(write-line "dim bottomElevation = item.endlocation(1,\"btm\") + (item.dim[1].value / 2)" writeToVBCode)
(write-line "dim floorLevel = item.level(\"floor\")" writeToVBCode)
(write-line "dim legLength = (bottomElevation-floorLevel)" writeToVBCode)
(write-line "item.dim[4].value = 0" writeToVBCode)
(write-line "item.dim[4].value = (0-1)" writeToVBCode)
(write-line "item.dim[3].value = 0" writeToVBCode)
(write-line "item.dim[3].value = ((item.dim[3].value - (item.dim[1].value / 2)) - legLength)" writeToVBCode)
(write-line "elseif (wildcard(item.filename,\"*Floor Mount Angle\") = 1) then" writeToVBCode)
(write-line "dim bottomElevation = item.endlocation(1,\"btm\") + (item.dim[1].value / 2)" writeToVBCode)
(write-line "dim floorLevel = item.level(\"floor\")" writeToVBCode)
(write-line "dim legLength = (bottomElevation-floorLevel)" writeToVBCode)
(write-line "item.dim[4].value = 0" writeToVBCode)
(write-line "item.dim[4].value = (0-1)" writeToVBCode)
(write-line "item.dim[3].value = 0" writeToVBCode)
(write-line "item.dim[3].value = ((item.dim[3].value - (item.dim[1].value / 2)) - legLength)" writeToVBCode)
(write-line (strcat "elseif (wildcard(item.filename,\"Floor Supports Post\") = 1) "
                        "or (wildcard(item.filename,\"Floor Supports Post Double\") = 1) "
                        "or (wildcard(item.filename,\"Floor Supports Post Round\") = 1) "
                        "or (wildcard(item.filename,\"Floor Support Post Single\") = 1) "
                        "or (wildcard(item.filename,\"Floor Supports Angle\") = 1) "
                        "or (wildcard(item.filename,\"Floor Supports Angle Double\") = 1) "
                        "or (wildcard(item.filename,\"Floor Supports Angle Round\") = 1) "
                        "or (wildcard(item.filename,\"Floor Support Angle Single\") = 1) then") writeToVBCode)
(write-line "dim bottomElevation = item.endlocation(1,\"btm\")" writeToVBCode)
(write-line "dim floorLevel = item.level(\"floor\")" writeToVBCode)
(write-line "dim legLength = (bottomElevation-floorLevel)" writeToVBCode)
(write-line "item.dim[\"Distance to Floor [#159]\"].value = legLength" writeToVBCode)
(write-line (strcat "elseif (wildcard(item.filename,\"Floor Support Post\") = 1) "
                        "or (wildcard(item.filename,\"Floor Support Post Double\") = 1) "
                        "or (wildcard(item.filename,\"Floor Support Post Round\") = 1) "
                        "or (wildcard(item.filename,\"Floor Support Angle\") = 1) "
                        "or (wildcard(item.filename,\"Floor Support Angle Double\") = 1) "
                        "or (wildcard(item.filename,\"Floor Support Angle Round\") = 1) then") writeToVBCode)
(write-line "dim bottomElevation = item.endlocation(1,\"btm\")" writeToVBCode)
(write-line "dim floorLevel = item.level(\"floor\")" writeToVBCode)
(write-line "dim legLength = (bottomElevation-floorLevel)" writeToVBCode)
(write-line "item.dim[\"Distance to Floor[#159]\"].value = legLength" writeToVBCode)
(write-line "rem Hanger Support ====================================================================================================" writeToVBCode)
(write-line "elseif (wildcard(item.service,\"*trimble*\") = 0) and (wildcard(item.servicetype,\"*Hanger\") = 1) and (wildcard(item.filename,\"*Wrap Round\") = 1) then" writeToVBCode)
(write-line "dim topElevation = item.endlocation(1,\"btm\") + item.dim[1].value" writeToVBCode)
(write-line "dim soffitLevel = item.level(\"soffit\")" writeToVBCode)
(write-line "dim hangLength = (soffitLevel-topElevation)" writeToVBCode)
(write-line "item.dim[2].value = hangLength" writeToVBCode)
(write-line "elseif (wildcard(item.service,\"*trimble*\") = 0) and (wildcard(item.servicetype,\"*Hanger\") = 1) and (wildcard(item.filename,\"*Strap Single\") = 1) then" writeToVBCode)
(write-line "dim topElevation = item.endlocation(1,\"btm\") + item.dim[2].value" writeToVBCode)
(write-line "dim soffitLevel = item.level(\"soffit\")" writeToVBCode)
(write-line "dim hangLength = (soffitLevel-topElevation)" writeToVBCode)
(write-line "item.dim[3].value = hangLength" writeToVBCode)
(write-line "elseif (wildcard(item.service,\"*trimble*\") = 0) and (wildcard(item.servicetype,\"*Hanger\") = 1) and (wildcard(item.filename,\"*Flat Strap (Round)\") = 1) then" writeToVBCode)
(write-line "dim topElevation = item.endlocation(1,\"btm\") + item.dim[1].value" writeToVBCode)
(write-line "dim soffitLevel = item.level(\"soffit\")" writeToVBCode)
(write-line "dim hangLength = (soffitLevel-topElevation)" writeToVBCode)
(write-line "item.dim[2].value = hangLength" writeToVBCode)
(write-line "elseif (wildcard(item.service,\"*trimble*\") = 0) and (wildcard(item.servicetype,\"*Hanger\") = 1) and (wildcard(item.filename,\"*Flat Strap (Rectangle)\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[3].value = hangLength" writeToVBCode)
(write-line "elseif (wildcard(item.service,\"*trimble*\") = 0) and (wildcard(item.servicetype,\"*Hanger\") = 1) and (wildcard(item.filename,\"*rectangular bearer\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[6].value = hangLength" writeToVBCode)
(write-line "rem Seismic Included Here =============================================================================================" writeToVBCode)
(write-line "elseif (wildcard(item.servicetype,\"*Seismic*\") = 1) and (wildcard(item.filename,\"Double Rectangular Bearer\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[\"Distance To Deck\"].value = hangLength" writeToVBCode)
(write-line "elseif (wildcard(item.servicetype,\"*Seismic*\") = 1) and (wildcard(item.filename,\"Seismic Rectangular\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[\"Distance To Deck\"].value = hangLength" writeToVBCode)
(write-line "elseif (wildcard(item.servicetype,\"*Seismic*\") = 1) and (wildcard(item.filename,\"Seismic\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[\"Distance to Anchor Z Axis [INDEX#15]\"].value = hangLength" writeToVBCode)
(write-line "elseif (wildcard(item.servicetype,\"*Seismic*\") = 1) and (wildcard(item.filename,\"Round Duct or Pipe Seismic\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[\"Distance to Anchor Z Axis [#15]\"].value = hangLength" writeToVBCode)
(write-line "elseif (wildcard(item.servicetype,\"*Seismic*\") = 1) and (wildcard(item.filename,\"Equipment Seismic\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[\"[EDIT] VERTICAL DISTANCE [#15]\"].value = hangLength" writeToVBCode)
(write-line "elseif (wildcard(item.servicetype,\"*Seismic*\") = 1) and (wildcard(item.filename,\"Rectangular Duct Seismic\") = 1) then" writeToVBCode)
(write-line "dim topElevation = item.endlocation(1,\"top\")" writeToVBCode)
(write-line "dim soffitLevel = item.level(\"soffit\")" writeToVBCode)
(write-line "dim hangLength = (soffitLevel-topElevation)" writeToVBCode)
(write-line "item.dim[\"[EDIT] VERTICAL DISTANCE [#15]\"].value = hangLength" writeToVBCode)
(write-line "end if" writeToVBCode)
(write-line "end select" writeToVBCode)
  (close writeToVBCode)
  (command "pselect" hangers "")
  (Executescript vbCode)
  (vl-file-delete vbCode)
  (prompt "All hangers have been stretched to their respective section heights.")(princ)
  
  (princ)
  (END_ROUTINE));end defun
;**************************************************************************************************************************************************
(defun c:Insulation_Specification_Cycle ()
  ;;;; ISC = CYCLES INSULATION SPECIFICATION OPTIONS WHERE APPROPRIATE
(OUTSIDE_LOOP_VARIABLES nil)
(write-line "requires task.selection" writeToVBCode)
(write-line "dim i = 1" writeToVBCode)
(write-line "task.beginprogress(task.selection.count)" writeToVBCode)
(write-line "while i <= task.selection.count" writeToVBCode)
(write-line "dim item = task.selection[i]" writeToVBCode)
(write-line "dim qt = ASCII(34)" writeToVBCode)
(write-line "REM ROUND EVALUATION" writeToVBCode)
(write-line "if item.insspec = \"INSULATION: Liner x 0.50\" then" writeToVBCode)
(write-line "item.insspec = \"INSULATION: Liner x 1.00\"" writeToVBCode)
(write-line "item.update()" writeToVBCode)
(write-line "elseif item.insspec = \"INSULATION: Liner x 1.00\" then" writeToVBCode)
(write-line "item.insspec = \"INSULATION: Liner x 1.50\"" writeToVBCode)
(write-line "item.update()" writeToVBCode)
(write-line "elseif item.insspec = \"INSULATION: Liner x 1.50\" then" writeToVBCode)
(write-line "item.insspec = \"INSULATION: Liner x 2.00\"" writeToVBCode)
(write-line "item.update()" writeToVBCode)
(write-line "elseif item.insspec = \"INSULATION: Liner x 2.00\" then" writeToVBCode)
(write-line "item.insspec = \"INSULATION: Duct Wrap x 1.00\"" writeToVBCode)
(write-line "item.update()" writeToVBCode)
(write-line "elseif item.insspec = \"INSULATION: Duct Wrap x 1.00\" then" writeToVBCode)
(write-line "item.insspec = \"INSULATION: Duct Wrap x 1.50\"" writeToVBCode)
(write-line "item.update()" writeToVBCode)
(write-line "elseif item.insspec = \"INSULATION: Duct Wrap x 1.50\" then" writeToVBCode)
(write-line "item.insspec = \"INSULATION: Duct Wrap x 2.00\"" writeToVBCode)
(write-line "item.update()" writeToVBCode)
(write-line "elseif item.insspec = \"INSULATION: Duct Wrap x 2.00\" then" writeToVBCode)
(write-line "item.insspec = \"INSULATION: Duct Wrap x 3.00\"" writeToVBCode)
(write-line "item.update()" writeToVBCode)
(write-line "elseif item.insspec = \"INSULATION: Duct Wrap x 3.00\" then" writeToVBCode)
(write-line "item.insspec = \"INSULATION: Duct Wrap x 4.00\"" writeToVBCode)
(write-line "item.update()" writeToVBCode)
(write-line "elseif item.insspec = \"INSULATION: Duct Wrap x 4.00\" then" writeToVBCode)
(write-line "item.insspec = \"INSULATION: Fire Wrap x 2.00\"" writeToVBCode)
(write-line "item.update()" writeToVBCode)
(write-line "elseif item.insspec = \"INSULATION: Fire Wrap x 2.00\" then" writeToVBCode)
(write-line "item.insspec = \"INSULATION: Fire Wrap x 3.00\"" writeToVBCode)
(write-line "item.update()" writeToVBCode)
(write-line "elseif item.insspec = \"INSULATION: Fire Wrap x 3.00\" then" writeToVBCode)
(write-line "item.insspec = \"INSULATION: Fire Wrap x 4.00\"" writeToVBCode)
(write-line "item.update()" writeToVBCode)
(write-line "elseif item.insspec = \"INSULATION: Fire Wrap x 4.00\" then" writeToVBCode)
(write-line "item.insspec = \"INSULATION: Fire Wrap x 5.00\"" writeToVBCode)
(write-line "item.update()" writeToVBCode)
(write-line "elseif item.insspec = \"INSULATION: Fire Wrap x 5.00\" then" writeToVBCode)
(write-line "item.insspec = \"INSULATION: Fire Wrap x 6.00\"" writeToVBCode)
(write-line "item.update()" writeToVBCode)
(write-line "elseif item.insspec = \"INSULATION: Fire Wrap x 6.00\" then" writeToVBCode)
(write-line "item.insspec = \"INSULATION: Fire Wrap x 7.00\"" writeToVBCode)
(write-line "item.update()" writeToVBCode)
(write-line "elseif item.insspec = \"INSULATION: Fire Wrap x 7.00\" then" writeToVBCode)
(write-line "item.insspec = \"INSULATION: Fire Wrap x 8.00\"" writeToVBCode)
(write-line "item.update()" writeToVBCode)
(write-line "elseif item.insspec = \"INSULATION: Fire Wrap x 8.00\" then" writeToVBCode)
(write-line "item.insspec = \"INSULATION: Fire Wrap x 9.00\"" writeToVBCode)
(write-line "item.update()" writeToVBCode)
(write-line "elseif item.insspec = \"INSULATION: Fire Wrap x 9.00\" then" writeToVBCode)
(write-line "item.insspec = \"INSULATION: Fire Wrap x 10.00\"" writeToVBCode)
(write-line "item.update()" writeToVBCode)
(write-line "elseif item.insspec = \"INSULATION: Fire Wrap x 10.00\" then" writeToVBCode)
(write-line "item.insspec = \"INSULATION: Double Wall x 0.50\"" writeToVBCode)
(write-line "item.update()" writeToVBCode)
(write-line "elseif item.insspec = \"INSULATION: Double Wall x 0.50\" then" writeToVBCode)
(write-line "item.insspec = \"INSULATION: Double Wall x 1.00\"" writeToVBCode)
(write-line "item.update()" writeToVBCode)
(write-line "elseif item.insspec = \"INSULATION: Double Wall x 1.00\" then" writeToVBCode)
(write-line "item.insspec = \"INSULATION: Double Wall x 1.50\"" writeToVBCode)
(write-line "item.update()" writeToVBCode)
(write-line "elseif item.insspec = \"INSULATION: Double Wall x 1.50\" then" writeToVBCode)
(write-line "item.insspec = \"INSULATION: Double Wall x 2.00\"" writeToVBCode)
(write-line "item.update()" writeToVBCode)
(write-line "elseif item.insspec = \"INSULATION: Double Wall x 2.00\" then" writeToVBCode)
(write-line "item.insspec = \"Off\"" writeToVBCode)
(write-line "item.update()" writeToVBCode)
(write-line "elseif item.insspec = \"Off\" then" writeToVBCode)
(write-line "item.insspec = \"None\"" writeToVBCode)
(write-line "item.update()" writeToVBCode)
(write-line "elseif item.insspec = \"Not Set\" then" writeToVBCode)
(write-line "item.insspec = \"INSULATION: Liner x 0.50\"" writeToVBCode)
(write-line "item.update()" writeToVBCode)
(write-line "end if" writeToVBCode)
(write-line "dim j = 1" writeToVBCode)
(write-line "while j < 100" writeToVBCode)
(write-line "task.message = \"You have just switched to:                            \" + item.insspec" writeToVBCode)
(write-line "j = j + 1" writeToVBCode)
(write-line "end while" writeToVBCode)
(write-line "i = i + 1" writeToVBCode)
(write-line "end while" writeToVBCode)
  (close writeToVBCode)
  (Executescript vbCode)
  (vl-file-delete vbCode)
  (prompt "Cycled to the next insulation specification option.")(princ)
  (princ)
(END_ROUTINE));end defun
;**************************************************************************************************************************************************
(defun c:Insulation_Cycle ()
;;;; IC = CYCLES INSULATION OPTIONS WHERE APPROPRIATE
(OUTSIDE_LOOP_VARIABLES nil)
(write-line "" writeToVBCode)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "item.ispeclock = false" writeToVBCode)
(write-line "item.insspec = \"None\"" writeToVBCode)
(write-line "item.ispeclock = true" writeToVBCode)
(write-line "if item.CID <> 838 then" writeToVBCode)
(write-line "if (wildcard(item.service,\"*exhaust*\") = 1) then" writeToVBCode)
(write-line "item.insulation.status = \"OFF\"" writeToVBCode)
(write-line "item.update()" writeToVBCode)
(write-line "elseif (wildcard(item.service,\"*exhaust*\") = 0) then" writeToVBCode)
(write-line "if item.insulation.status = \"OFF\" then" writeToVBCode)
(write-line "item.insulation.status = \"OUTSIDE\"" writeToVBCode)
(write-line "item.insulation.material = \"HVAC Liner: Duct Wrap\"" writeToVBCode)
(write-line "item.insulation.gauge = 1.5" writeToVBCode)
(write-line "item.update()" writeToVBCode)
(write-line "elseif item.insulation.status = \"OUTSIDE\" then" writeToVBCode)
(write-line "item.insulation.status = \"INSIDE\"" writeToVBCode)
(write-line "item.insulation.material = \"HVAC Liner: 1-1/2 LB\"" writeToVBCode)
(write-line "item.insulation.gauge = 1" writeToVBCode)
(write-line "item.update()" writeToVBCode)
(write-line "elseif (item.insulation.status = \"INSIDE\") then" writeToVBCode)
(write-line "item.insulation.status = \"OFF\"" writeToVBCode)
(write-line "item.update()" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (prompt "Cycled to the next insulation option.")(princ)
  (princ)
(END_ROUTINE));end defun
;**************************************************************************************************************************************************
(defun c:Insulation_Gauge_Cycle ()
;;;; IG = CYCLES INSULATION GAUGE WHERE APPROPRIATE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if (wildcard(item.insulation.material,\"Duct Wrap\")=1) then" writeToVBCode)
(write-line "if (item.insulation.gauge = 1.5) then" writeToVBCode)
(write-line "item.insulation.gauge = 2" writeToVBCode)
(write-line "elseif (item.insulation.gauge = 2) then" writeToVBCode)
(write-line "item.insulation.gauge = 3" writeToVBCode)
(write-line "elseif (item.insulation.gauge = 3) then" writeToVBCode)
(write-line "item.insulation.gauge = 4" writeToVBCode)
(write-line "elseif (item.insulation.gauge = 4) then" writeToVBCode)
(write-line "item.insulation.gauge = 1" writeToVBCode)
(write-line "elseif (item.insulation.gauge = 1) then" writeToVBCode)
(write-line "item.insulation.gauge = 1.5" writeToVBCode)
(write-line "end if" writeToVBCode)
(write-line "elseif (wildcard(item.insulation.material,\"1-1/2 LB\")=1) and (item.doublewall = false) then" writeToVBCode)
(write-line "if (item.insulation.gauge = 1) then" writeToVBCode)
(write-line "item.insulation.gauge = 1.5" writeToVBCode)
(write-line "elseif (item.insulation.gauge = 1.5) then" writeToVBCode)
(write-line "item.insulation.gauge = 2" writeToVBCode)
(write-line "elseif (item.insulation.gauge = 2) then" writeToVBCode)
(write-line "item.insulation.gauge = 0.5" writeToVBCode)
(write-line "elseif (item.insulation.gauge = 0.5) then" writeToVBCode)
(write-line "item.insulation.gauge = 1" writeToVBCode)
(write-line "end if" writeToVBCode)
(write-line "elseif (wildcard(item.insulation.material,\"Fire Barrier Duct Wrap\")=1) then" writeToVBCode)
(write-line "if (item.insulation.gauge = 2) then" writeToVBCode)
(write-line "item.insulation.gauge = 3" writeToVBCode)
(write-line "elseif (item.insulation.gauge = 3) then" writeToVBCode)
(write-line "item.insulation.gauge = 4" writeToVBCode)
(write-line "elseif (item.insulation.gauge = 4) then" writeToVBCode)
(write-line "item.insulation.gauge = 5" writeToVBCode)
(write-line "elseif (item.insulation.gauge = 5) then" writeToVBCode)
(write-line "item.insulation.gauge = 6" writeToVBCode)
(write-line "elseif (item.insulation.gauge = 6) then" writeToVBCode)
(write-line "item.insulation.gauge = 7" writeToVBCode)
(write-line "elseif (item.insulation.gauge = 7) then" writeToVBCode)
(write-line "item.insulation.gauge = 8" writeToVBCode)
(write-line "elseif (item.insulation.gauge = 8) then" writeToVBCode)
(write-line "item.insulation.gauge = 9" writeToVBCode)
(write-line "elseif (item.insulation.gauge = 9) then" writeToVBCode)
(write-line "item.insulation.gauge = 10" writeToVBCode)
(write-line "elseif (item.insulation.gauge = 10) then" writeToVBCode)
(write-line "item.insulation.gauge = 2" writeToVBCode)
(write-line "end if" writeToVBCode)
(write-line "elseif item.doublewall = true then" writeToVBCode)
(write-line "if (item.insulation.gauge = 1) then" writeToVBCode)
(write-line "item.insulation.gauge = 1.5" writeToVBCode)
(write-line "elseif (item.insulation.gauge = 1.5) then" writeToVBCode)
(write-line "item.insulation.gauge = 2" writeToVBCode)
(write-line "elseif (item.insulation.gauge = 2) then" writeToVBCode)
(write-line "item.insulation.gauge = 0.5" writeToVBCode)
(write-line "elseif (item.insulation.gauge = 0.5) then" writeToVBCode)
(write-line "item.insulation.gauge = 1" writeToVBCode)
(write-line "end if" writeToVBCode)
(write-line "item.update()" writeToVBCode)
(write-line "end if" writeToVBCode)
(write-line "item.update()" writeToVBCode)
(write-line "i = i + 1" writeToVBCode)
(write-line "end while" writeToVBCode)
  (close writeToVBCode)
  (Executescript vbCode)
  (vl-file-delete vbCode)
  (prompt "Cycled insulation gauge")(princ)
  (princ)
(END_ROUTINE));end defun
;**************************************************************************************************************************************************
;;;; TEXT LAYER - SWITCHES LAYER TO TEXT
(defun c:Make_Text_Layer_Current ()
  (COMMAND "LAYER" "SET" "M-AMC-TEXT" "")
  (prompt "Current Layer is now TEXT")(princ)
  (princ)
(END_ROUTINE));end defun
;**************************************************************************************************************************************************
;;;; FLEXFILL
(defun c:FLEX_FILL ()
  (command "FLEXFILL")
  (princ)
(END_ROUTINE));end defun
;**************************************************************************************************************************************************
;;;; TO TURN ON SIZE & ELEVATION AT THE SAME TIME WITH ONE BUTTON
(defun c:Size_&_Elevation_Cycle ()
  (setq sset (ssget)
	i 0);end setq
  (OUTSIDE_LOOP_VARIABLES sset)
  (while (< i Limit)
  (INSIDE_LOOP_VARIABLES sset i)
   (if(or(and(= SizeToggle "On")(= ElevationToggle "Off"))(and(= SizeToggle "Off")(= ElevationToggle "On")))
     (settext SSentity 6 "off")
     (if(and(not(= SizeToggle "On"))(not(= ElevationToggle "On")))
       (settext SSentity 6 "on")
       (if(and(= SizeToggle "On")(= ElevationToggle "On"))
         (settext SSentity 4 "Off")
   ) ) );end if
   (setq i (1+ i))
  );end while
  (command "pselect" sset "")
  (command "regen")
  (princ)
(END_ROUTINE));end defun
;**************************************************************************************************************************************************
(defun c:Text_Toggle_Number ()
  (setq sset (ssget '((0 . "MAPS_SOLID")))
	i 0);end setq
  (OUTSIDE_LOOP_VARIABLES sset)
  (while (< i Limit)
  (INSIDE_LOOP_VARIABLES sset i)
   (if(= NumberToggle "On")
     (settext SSentity 1 "off")
     (if(not(= NumberToggle "On"))
       (settext SSentity 1 "on")
   ) );end if
   (setq i (1+ i))
  );end while
  (command "pselect" sset "")
  (command "regen")
  (princ)
(END_ROUTINE));end defun
;**************************************************************************************************************************************************
(defun c:Text_Toggle_Size ()
  (setq sset (ssget '((0 . "MAPS_SOLID")))
	i 0);end setq
  (OUTSIDE_LOOP_VARIABLES sset)
  (while (< i Limit)
  (INSIDE_LOOP_VARIABLES sset i)
   (if(= SizeToggle "On")
     (settext SSentity 2 "off")
     (if(not(= SizeToggle "On"))
       (settext SSentity 2 "on")
   ) );end if
   (setq i (1+ i))
  );end while
  (command "pselect" sset "")
  (command "regen")
  (princ)
(END_ROUTINE));end defun
;**************************************************************************************************************************************************
(defun c:Text_Toggle_Elevation ()
  (setq sset (ssget '((0 . "MAPS_SOLID")))
	i 0);end setq
  (OUTSIDE_LOOP_VARIABLES sset)
  (while (< i Limit)
  (INSIDE_LOOP_VARIABLES sset i)
   (if(= ElevationToggle "On")
     (settext SSentity 4 "off")
     (if(not(= ElevationToggle "On"))
       (settext SSentity 4 "on")
   ) );end if
   (setq i (1+ i))
  );end while
  (command "pselect" sset "")
  (command "regen")
  (princ)
(END_ROUTINE));end defun
;**************************************************************************************************************************************************
(defun c:Text_Toggle_Alias ()
  (setq sset (ssget '((0 . "MAPS_SOLID")))
	i 0);end setq
  (OUTSIDE_LOOP_VARIABLES sset)
  (while (< i Limit)
  (INSIDE_LOOP_VARIABLES sset i)
   (if(= AliasToggle "On")
     (settext SSentity 8 "off")
     (if(not(= AliasToggle "On"))
       (settext SSentity 8 "on")
   ) );end if
   (setq i (1+ i))
  );end while
  (command "pselect" sset "")
  (command "regen")
  (princ)
(END_ROUTINE));end defun
;**************************************************************************************************************************************************
(defun c:Text_Toggle_Offset ()
  (setq sset (ssget '((0 . "MAPS_SOLID")))
	i 0);end setq
  (OUTSIDE_LOOP_VARIABLES sset)
  (while (< i Limit)
  (INSIDE_LOOP_VARIABLES sset i)
   (if(= OffsetToggle "On")
     (settext SSentity 16 "off")
     (if(not(= OffsetToggle "On"))
       (settext SSentity 16 "on")
   ) );end if
   (setq i (1+ i))
  );end while
  (command "pselect" sset "")
  (command "regen")
  (princ)
(END_ROUTINE));end defun
;**************************************************************************************************************************************************
(defun c:Text_Toggle_Length ()
  (setq sset (ssget '((0 . "MAPS_SOLID")))
	i 0);end setq
  (OUTSIDE_LOOP_VARIABLES sset)
  (while (< i Limit)
  (INSIDE_LOOP_VARIABLES sset i)
   (if(= LengthToggle "On")
     (settext SSentity 32 "off")
     (if(not(= LengthToggle "On"))
       (settext SSentity 32 "on")
   ) );end if
   (setq i (1+ i))
  );end while
  (command "pselect" sset "")
  (command "regen")
  (princ)
(END_ROUTINE));end defun
;**************************************************************************************************************************************************
(defun c:Text_Numbers_On ()
  (settext (ssget (mapfilter "#39 = 330 | #39 = 8 | #39 = 7 | #39 = 505 | #39 = 20 | #39 = 30 | #39 = 68 | #39 = 2 | #39 = 838 | #39 = 866 | #107 = E.C.")) 1 "on")
  (print "Numbers On")
  (princ)
(END_ROUTINE));end defun
;**************************************************************************************************************************************************
(defun c:Text_Numbers_Off (/)
  (settext (ssget "X" '((0 . "MAPS_SOLID"))) 1 "off")
  (print "Numbers Off")
  (princ)
(END_ROUTINE));end defun
;**************************************************************************************************************************************************
(defun c:Text_Size_On (/)
  (settext (ssget '((0 . "MAPS_SOLID"))) 2 "on")
  (print "Size On")
  (princ)
(END_ROUTINE));end defun
;**************************************************************************************************************************************************
(defun c:Text_Size_Off (/)
  (settext (ssget '((0 . "MAPS_SOLID"))) 2 "off")
  (print "Size Off")
  (princ)
(END_ROUTINE));end defun
;**************************************************************************************************************************************************
(defun c:Text_Elevation_On (/)
  (settext (ssget '((0 . "MAPS_SOLID"))) 4 "on")
  (print "Elevation On")
  (princ)
(END_ROUTINE));end defun
;**************************************************************************************************************************************************
(defun c:Text_Elevation_Off (/)
  (settext (ssget '((0 . "MAPS_SOLID"))) 4 "off")
  (print "Elevation Off")
  (princ)
(END_ROUTINE));end defun
;**************************************************************************************************************************************************
(defun c:Text_Alias_On (/)
  (settext (ssget '((0 . "MAPS_SOLID"))) 8 "on")
  (print "Alias On")
  (princ)
(END_ROUTINE));end defun
;**************************************************************************************************************************************************
(defun c:Text_Alias_Off (/)
  (settext (ssget '((0 . "MAPS_SOLID"))) 8 "off")
  (print "Alias Off")
  (princ)
(END_ROUTINE));end defun
;**************************************************************************************************************************************************
(defun c:Text_Offset_On (/)
  (settext (ssget '((0 . "MAPS_SOLID"))) 16 "on")
  (print "Offset On")
  (princ)
(END_ROUTINE));end defun
;**************************************************************************************************************************************************
(defun c:Text_Offset_Off (/)
  (settext (ssget '((0 . "MAPS_SOLID"))) 16 "off")
  (print "Offset Off")
  (princ)
(END_ROUTINE));end defun
;**************************************************************************************************************************************************
(defun c:Text_Length_On (/)
  (settext (ssget '((0 . "MAPS_SOLID"))) 32 "on")
  (print "Length On")
  (princ)
(END_ROUTINE));end defun
;**************************************************************************************************************************************************
(defun c:Text_Length_Off (/)
  (settext (ssget '((0 . "MAPS_SOLID"))) 32 "off")
  (print "Length Off")
  (princ)
(END_ROUTINE));end defun
;**************************************************************************************************************************************************
;;;; TO - TEXT ON - TEXT TURNED ON!!
(defun c:Text_All_On (/)
  (settext(ssget) 63 "on")
  (print "All Text On")
  (princ)
(END_ROUTINE));end defun
;**************************************************************************************************************************************************
;;;; TF - TEXT OFF - REMOVE TEXT FROM THE CURRENT DRAWING !!CAUTION!! THIS WIPES THE MEMORY OF WHICH ITEMS HAD WHICH TEXT TURNED ON!!
(defun c:Text_All_Off (/)
  (settext(ssget) 63 "off")
  (print "All Text Off")
  (princ)
(END_ROUTINE));end defun
;**************************************************************************************************************************************************
(defun c:DeBug_Script ()
  ;;;; DB = CALLS UP THE DEBUG TEST FILE
  (OUTSIDE_LOOP_VARIABLES nil)
  (Executescript debugFileLink)
  (princ)
(END_ROUTINE));end defun
;**************************************************************************************************************************************************
(defun c:Size_Down_Item ()
;;;; SD = SIZE DOWN Reduce fitting size by one index location
(OUTSIDE_LOOP_VARIABLES nil)
(write-line "requires task.selection" writeToVBCode)
(write-line "dim i = 1" writeToVBCode)
(write-line "while i <= task.selection.count" writeToVBCode)
(write-line "dim item = task.selection[i]" writeToVBCode)
(write-line "rem THIS INCREMENTS DOWN" writeToVBCode)
(write-line "if item.hasproduct then" writeToVBCode)
(write-line "dim entry" writeToVBCode)
(write-line "dim desc=item.description" writeToVBCode)
(write-line "for entry=1 to item.product.entries" writeToVBCode)
(write-line "if desc=item.product.entry[entry].name then" writeToVBCode)
(write-line "dim index=entry-1" writeToVBCode)
(write-line "if index > 0 then" writeToVBCode)
(write-line "dim entry=item.product.entries" writeToVBCode)
(write-line "item.description=item.product.entry[index].name" writeToVBCode)
(write-line "endif" writeToVBCode)
(write-line "endif" writeToVBCode)
(write-line "next" writeToVBCode)
(write-line "item.update()" writeToVBCode)
(write-line "elseif item.hasproduct=false then" writeToVBCode)
(write-line "if item.dim[1].value <= 11 and item.CID <> 818 then" writeToVBCode)
(write-line "if (item.CID = 40 or item.CID = 522 or item.CID = 523 or item.CID = 873 or item.CID = 856 or item.CID = 68 or item.CID = 1112 or item.CID = 51 or item.CID = 61) or (wildcard(item.filename,\"*Flat Strap (Round)\") = 1) or (wildcard(item.filename,\"*Wrap Round\") = 1) or (wildcard(item.filename,\"*round floor mount\") = 1) then" writeToVBCode)
(write-line "item.dim[1].value = item.dim[1].value - 1" writeToVBCode)
(write-line "item.update()" writeToVBCode)
(write-line "elseif (item.CID = 866 or item.CID = 802 or item.CID = 30 or item.CID = 535 or item.CID = 382 or item.CID = 1 or item.CID = 505 or item.CID = 166) or (wildcard(item.filename,\"*rectangular floor mount\") = 1) or (wildcard(item.filename,\"*Flat Strap (Rectangle)\") = 1) or (wildcard(item.filename,\"*rectangular bearer\") = 1) then" writeToVBCode)
(write-line "item.dim[1].value = item.dim[1].value - 1" writeToVBCode)
(write-line "item.dim[2].value = item.dim[2].value - 1" writeToVBCode)
(write-line "item.update()" writeToVBCode)
(write-line "elseif item.CID = 20 or item.CID = 17 or item.CID = 8 then" writeToVBCode)
(write-line "item.dim[1].value = item.dim[1].value - 1" writeToVBCode)
(write-line "item.dim[2].value = item.dim[2].value - 1" writeToVBCode)
(write-line "if (wildcard(item.dim[3].value,\"Equal\") = 1) then" writeToVBCode)
(write-line "item.dim[3].value = item.dim[1].value - 1" writeToVBCode)
(write-line "elseif (wildcard(item.dim[3].value,\"Equal\") = 0) then" writeToVBCode)
(write-line "item.dim[3].value = item.dim[3].value - 1" writeToVBCode)
(write-line "item.update()" writeToVBCode)
(write-line "end if" writeToVBCode)
(write-line "item.update()" writeToVBCode)
(write-line "elseif item.CID = 330 or item.CID = 2 then" writeToVBCode)
(write-line "item.dim[1].value = item.dim[1].value - 1" writeToVBCode)
(write-line "item.dim[2].value = item.dim[2].value - 1" writeToVBCode)
(write-line "item.dim[3].value = item.dim[3].value - 1" writeToVBCode)
(write-line "item.dim[4].value = item.dim[4].value - 1" writeToVBCode)
(write-line "end if" writeToVBCode)
(write-line "elseif item.dim[1].value > 11 and item.CID <> 818 then" writeToVBCode)
(write-line "if (item.CID = 40 or item.CID = 522 or item.CID = 523 or item.CID = 873 or item.CID = 856 or item.CID = 68 or item.CID = 1112 or item.CID = 51 or item.CID = 61) or (wildcard(item.filename,\"*Flat Strap (Round)\") = 1) or (wildcard(item.filename,\"*Wrap Round\") = 1) or (wildcard(item.filename,\"*round floor mount\") = 1) then" writeToVBCode)
(write-line "item.dim[1].value = item.dim[1].value - 2" writeToVBCode)
(write-line "item.update()" writeToVBCode)
(write-line "elseif (item.CID = 866 or item.CID = 802 or item.CID = 30 or item.CID = 535 or item.CID = 382 or item.CID = 1 or item.CID = 505 or item.CID = 166) or (wildcard(item.filename,\"*rectangular floor mount\") = 1) or (wildcard(item.filename,\"*Flat Strap (Rectangle)\") = 1) or (wildcard(item.filename,\"*rectangular bearer\") = 1) then" writeToVBCode)
(write-line "item.dim[1].value = item.dim[1].value - 2" writeToVBCode)
(write-line "item.dim[2].value = item.dim[2].value - 2" writeToVBCode)
(write-line "item.update()" writeToVBCode)
(write-line "elseif item.CID = 20 or item.CID = 17 or item.CID = 8 then" writeToVBCode)
(write-line "item.dim[1].value = item.dim[1].value - 2" writeToVBCode)
(write-line "item.dim[2].value = item.dim[2].value - 2" writeToVBCode)
(write-line "if (wildcard(item.dim[3].value,\"Equal\") = 1) then" writeToVBCode)
(write-line "item.dim[3].value = item.dim[1].value" writeToVBCode)
(write-line "elseif (wildcard(item.dim[3].value,\"Equal\") = 0) then" writeToVBCode)
(write-line "item.dim[3].value = item.dim[3].value - 2" writeToVBCode)
(write-line "item.update()" writeToVBCode)
(write-line "end if" writeToVBCode)
(write-line "item.update()" writeToVBCode)
(write-line "elseif item.CID = 330 or item.CID = 2 then" writeToVBCode)
(write-line "item.dim[1].value = item.dim[1].value - 2" writeToVBCode)
(write-line "item.dim[2].value = item.dim[2].value - 2" writeToVBCode)
(write-line "item.dim[3].value = item.dim[3].value - 2" writeToVBCode)
(write-line "if (wildcard(item.dim[3].value,\"Equal\") = 1) then" writeToVBCode)
(write-line "item.dim[4].value = item.dim[2].value" writeToVBCode)
(write-line "item.update()" writeToVBCode)
(write-line "elseif (wildcard(item.dim[3].value,\"Equal\") = 0) then" writeToVBCode)
(write-line "item.dim[4].value = item.dim[4].value - 2" writeToVBCode)
(write-line "item.update()" writeToVBCode)
(write-line "end if    item.update()" writeToVBCode)
(write-line "end if" writeToVBCode)
(write-line "item.update()" writeToVBCode)
(write-line "elseif item.CID = 818 then" writeToVBCode)
(write-line "item.dim[\"Branch Width #1\"].value = item.dim[\"Branch Width #1\"].value - 2" writeToVBCode)
(write-line "item.dim[\"Branch Depth #1\"].value = item.dim[\"Branch Depth #1\"].value - 2" writeToVBCode)
(write-line "end if" writeToVBCode)
(write-line "item.update()" writeToVBCode)
(write-line "end if" writeToVBCode)
(write-line "i = i + 1" writeToVBCode)
(write-line "endwhile" writeToVBCode)
  (close writeToVBCode)
  (Executescript vbCode)
  (vl-file-delete vbCode)
  (princ)
(END_ROUTINE));end defun
;**************************************************************************************************************************************************
(defun c:Size_Up_Item ()
;;;; SU = SIZE UP Increase Fitting size by one index location
(OUTSIDE_LOOP_VARIABLES nil)
(write-line "requires task.selection" writeToVBCode)
(write-line "dim i = 1" writeToVBCode)
(write-line "while i <= task.selection.count" writeToVBCode)
(write-line "dim item = task.selection[i]" writeToVBCode)
(write-line "rem THIS INCREMENTS UP" writeToVBCode)
(write-line "if item.hasproduct then" writeToVBCode)
(write-line "dim entry" writeToVBCode)
(write-line "dim desc=item.description" writeToVBCode)
(write-line "for entry=1 to item.product.entries" writeToVBCode)
(write-line "if desc=item.product.entry[entry].name then" writeToVBCode)
(write-line "dim index=entry+1" writeToVBCode)
(write-line "if entry < item.product.entries then" writeToVBCode)
(write-line "dim entry=item.product.entries" writeToVBCode)
(write-line "item.description=item.product.entry[index].name" writeToVBCode)
(write-line "endif" writeToVBCode)
(write-line "endif" writeToVBCode)
(write-line "next" writeToVBCode)
(write-line "item.update()" writeToVBCode)
(write-line "elseif item.hasproduct=false then" writeToVBCode)
(write-line "if item.dim[1].value <= 11 and item.CID <> 818 then" writeToVBCode)
(write-line "if (item.CID = 40 or item.CID = 522 or item.CID = 523 or item.CID = 873 or item.CID = 856 or item.CID = 68 or item.CID = 1112 or item.CID = 51 or item.CID = 61) or (wildcard(item.filename,\"*Flat Strap (Round)\") = 1) or (wildcard(item.filename,\"*Wrap Round\") = 1) or (wildcard(item.filename,\"*round floor mount\") = 1) then" writeToVBCode)
(write-line "item.dim[1].value = item.dim[1].value + 1" writeToVBCode)
(write-line "item.update()" writeToVBCode)
(write-line "elseif (item.CID = 866 or item.CID = 802 or item.CID = 30 or item.CID = 535 or item.CID = 382 or item.CID = 1 or item.CID = 505 or item.CID = 166) or (wildcard(item.filename,\"*rectangular floor mount\") = 1) or (wildcard(item.filename,\"*Flat Strap (Rectangle)\") = 1) or (wildcard(item.filename,\"*rectangular bearer\") = 1) then" writeToVBCode)
(write-line "item.dim[1].value = item.dim[1].value + 1" writeToVBCode)
(write-line "item.dim[2].value = item.dim[2].value + 1" writeToVBCode)
(write-line "item.update()" writeToVBCode)
(write-line "elseif item.CID = 20 or item.CID = 17 or item.CID = 8 then" writeToVBCode)
(write-line "item.dim[1].value = item.dim[1].value + 1" writeToVBCode)
(write-line "item.dim[2].value = item.dim[2].value + 1" writeToVBCode)
(write-line "item.dim[3].value = item.dim[3].numvalue + 1" writeToVBCode)
(write-line "item.update()" writeToVBCode)
(write-line "elseif item.CID = 330 or item.CID = 2 then" writeToVBCode)
(write-line "item.dim[1].value = item.dim[1].value + 1" writeToVBCode)
(write-line "item.dim[2].value = item.dim[2].value + 1" writeToVBCode)
(write-line "item.dim[3].value = item.dim[3].value + 1" writeToVBCode)
(write-line "item.dim[4].value = item.dim[4].value + 1" writeToVBCode)
(write-line "end if" writeToVBCode)
(write-line "elseif item.dim[1].value > 11 and item.CID <> 818 then" writeToVBCode)
(write-line "if (item.CID = 40 or item.CID = 522 or item.CID = 523 or item.CID = 873 or item.CID = 856 or item.CID = 68 or item.CID = 1112 or item.CID = 51 or item.CID = 61) or (wildcard(item.filename,\"*Flat Strap (Round)\") = 1) or (wildcard(item.filename,\"*Wrap Round\") = 1) or (wildcard(item.filename,\"*round floor mount\") = 1) then" writeToVBCode)
(write-line "item.dim[1].value = item.dim[1].value + 2" writeToVBCode)
(write-line "item.update()" writeToVBCode)
(write-line "elseif (item.CID = 866 or item.CID = 802 or item.CID = 30 or item.CID = 535 or item.CID = 382 or item.CID = 1 or item.CID = 505 or item.CID = 166) or (wildcard(item.filename,\"*rectangular floor mount\") = 1) or (wildcard(item.filename,\"*Flat Strap (Rectangle)\") = 1) or (wildcard(item.filename,\"*rectangular bearer\") = 1) then" writeToVBCode)
(write-line "item.dim[1].value = item.dim[1].value + 2" writeToVBCode)
(write-line "item.dim[2].value = item.dim[2].value + 2" writeToVBCode)
(write-line "item.update()" writeToVBCode)
(write-line "elseif item.CID = 20 or item.CID = 17 or item.CID = 8 then" writeToVBCode)
(write-line "item.dim[1].value = item.dim[1].value + 2" writeToVBCode)
(write-line "item.dim[2].value = item.dim[2].value + 2" writeToVBCode)
(write-line "item.dim[3].value = item.dim[3].numvalue + 2" writeToVBCode)
(write-line "item.update()" writeToVBCode)
(write-line "elseif item.CID = 330 or item.CID = 2 then" writeToVBCode)
(write-line "item.dim[1].value = item.dim[1].value + 2" writeToVBCode)
(write-line "item.dim[2].value = item.dim[2].value + 2" writeToVBCode)
(write-line "item.dim[3].value = item.dim[3].value + 2" writeToVBCode)
(write-line "item.dim[4].value = item.dim[4].numvalue + 2" writeToVBCode)
(write-line "item.update()" writeToVBCode)
(write-line "end if" writeToVBCode)
(write-line "elseif item.CID = 818 then" writeToVBCode)
(write-line "item.dim[\"Branch Width #1\"].value = item.dim[\"Branch Width #1\"].value + 2" writeToVBCode)
(write-line "item.dim[\"Branch Depth #1\"].value = item.dim[\"Branch Depth #1\"].value + 2" writeToVBCode)
(write-line "end if" writeToVBCode)
(write-line "item.update()" writeToVBCode)
(write-line "end if" writeToVBCode)
(write-line "i = i + 1" writeToVBCode)
(write-line "endwhile" writeToVBCode)
(close writeToVBCode)
(Executescript vbCode)
(vl-file-delete vbCode)
(princ)
(END_ROUTINE));end defun
;**************************************************************************************************************************************************
(defun c:Update_Existing_Dampers ()
;;;; 38Rod = Switch Damper to 3/8" Rod
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.dampers > 0 then" writeToVBCode)
(write-line "if item.dampers = 1 then" writeToVBCode)
(write-line "if item.damper[1].value = \"3/8\"+qt+\" ROD-L\" or item.damper[2].value = \"3/8\"+qt+\" ROD-R\" or item.damper[2].value = \"3/8\"+qt+\" ROD-UP\" or item.damper[2].value = \"3/8\"+qt+\" ROD-DN\" then" writeToVBCode)
(write-line "item.damper[1].value = \"3/8\"+qt+\" ROD-D2\"" writeToVBCode)
(write-line "item.damper[1].locked = true" writeToVBCode)
(write-line "end if" writeToVBCode)
(write-line "if item.damper[1].value = \"KS7L-L\" or item.damper[2].value = \"KS7L-R\" or item.damper[2].value = \"KS7L-UP\" or item.damper[2].value = \"KS7L-DN\" then" writeToVBCode)
(write-line "item.damper[1].value = \"KS7L-D2\"" writeToVBCode)
(write-line "item.damper[1].locked = true" writeToVBCode)
(write-line "end if" writeToVBCode)
(write-line "elseif item.dampers = 2 then" writeToVBCode)
(write-line "if item.damper[1].value = \"3/8\"+qt+\" ROD-L\" or item.damper[2].value = \"3/8\"+qt+\" ROD-R\" or item.damper[2].value = \"3/8\"+qt+\" ROD-UP\" or item.damper[2].value = \"3/8\"+qt+\" ROD-DN\" then" writeToVBCode)
(write-line "item.damper[1].value = \"3/8\"+qt+\" ROD-D2\"" writeToVBCode)
(write-line "item.damper[1].locked = true" writeToVBCode)
(write-line "end if" writeToVBCode)
(write-line "if item.damper[1].value = \"KS7L-L\" or item.damper[2].value = \"KS7L-R\" or item.damper[2].value = \"KS7L-UP\" or item.damper[2].value = \"KS7L-DN\" then" writeToVBCode)
(write-line "item.damper[1].value = \"KS7L-D2\"" writeToVBCode)
(write-line "item.damper[1].locked = true" writeToVBCode)
(write-line "end if" writeToVBCode)
(write-line "if item.damper[2].value = \"3/8\"+qt+\" ROD-L\" or item.damper[2].value = \"3/8\"+qt+\" ROD-R\" or item.damper[2].value = \"3/8\"+qt+\" ROD-UP\" or item.damper[2].value = \"3/8\"+qt+\" ROD-DN\" then" writeToVBCode)
(write-line "item.damper[2].value = \"3/8\"+qt+\" ROD-D2\"" writeToVBCode)
(write-line "item.damper[2].locked = true" writeToVBCode)
(write-line "elseif item.damper[2].value = \"KS7L-L\" or item.damper[2].value = \"KS7L-R\" or item.damper[2].value = \"KS7L-UP\" or item.damper[2].value = \"KS7L-DN\" then" writeToVBCode)
(write-line "item.damper[2].value = \"KS7L-D2\"" writeToVBCode)
(write-line "item.damper[2].locked = true" writeToVBCode)
(write-line "end if" writeToVBCode)
(write-line "elseif item.dampers = 3 then" writeToVBCode)
(write-line "if item.damper[1].value = \"3/8\"+qt+\" ROD-L\" or item.damper[2].value = \"3/8\"+qt+\" ROD-R\" or item.damper[2].value = \"3/8\"+qt+\" ROD-UP\" or item.damper[2].value = \"3/8\"+qt+\" ROD-DN\" then" writeToVBCode)
(write-line "item.damper[1].value = \"3/8\"+qt+\" ROD-D2\"" writeToVBCode)
(write-line "item.damper[1].locked = true" writeToVBCode)
(write-line "elseif item.damper[1].value = \"KS7L-L\" or item.damper[2].value = \"KS7L-R\" or item.damper[2].value = \"KS7L-UP\" or item.damper[2].value = \"KS7L-DN\" then" writeToVBCode)
(write-line "item.damper[1].value = \"KS7L-D2\"" writeToVBCode)
(write-line "item.damper[1].locked = true" writeToVBCode)
(write-line "end if" writeToVBCode)
(write-line "if item.damper[2].value = \"3/8\"+qt+\" ROD-L\" or item.damper[2].value = \"3/8\"+qt+\" ROD-R\" or item.damper[2].value = \"3/8\"+qt+\" ROD-UP\" or item.damper[2].value = \"3/8\"+qt+\" ROD-DN\" then" writeToVBCode)
(write-line "item.damper[2].value = \"3/8\"+qt+\" ROD-D2\"" writeToVBCode)
(write-line "item.damper[2].locked = true" writeToVBCode)
(write-line "elseif item.damper[2].value = \"KS7L-L\" or item.damper[2].value = \"KS7L-R\" or item.damper[2].value = \"KS7L-UP\" or item.damper[2].value = \"KS7L-DN\" then" writeToVBCode)
(write-line "item.damper[2].value = \"KS7L-D2\"" writeToVBCode)
(write-line "item.damper[2].locked = true" writeToVBCode)
(write-line "end if" writeToVBCode)
(write-line "if item.damper[3].value = \"3/8\"+qt+\" ROD-L\" or item.damper[3].value = \"3/8\"+qt+\" ROD-D2\" then" writeToVBCode)
(write-line "item.damper[3].value = \"3/8\"+qt+\" ROD-UP\"" writeToVBCode)
(write-line "item.damper[3].locked = true" writeToVBCode)
(write-line "elseif item.damper[3].value = \"3/8\"+qt+\" ROD-R\" then" writeToVBCode)
(write-line "item.damper[3].value = \"3/8\"+qt+\" ROD-DN\"" writeToVBCode)
(write-line "item.damper[3].locked = true" writeToVBCode)
(write-line "elseif item.damper[3].value = \"KS7L-L\" or item.damper[3].value = \"KS7L-D2\" then" writeToVBCode)
(write-line "item.damper[3].value = \"KS7L-UP\"" writeToVBCode)
(write-line "item.damper[3].locked = true" writeToVBCode)
(write-line "elseif item.damper[3].value = \"KS7L-R\" then" writeToVBCode)
(write-line "item.damper[3].value = \"KS7L-DN\"" writeToVBCode)
(write-line "item.damper[3].locked = true" writeToVBCode)
(write-line "end if" writeToVBCode)
(write-line "elseif item.dampers = 4 then" writeToVBCode)
(write-line "if item.damper[1].value = \"3/8\"+qt+\" ROD-L\" or item.damper[2].value = \"3/8\"+qt+\" ROD-R\" or item.damper[2].value = \"3/8\"+qt+\" ROD-UP\" or item.damper[2].value = \"3/8\"+qt+\" ROD-DN\" then" writeToVBCode)
(write-line "item.damper[1].value = \"3/8\"+qt+\" ROD-D2\"" writeToVBCode)
(write-line "item.damper[1].locked = true" writeToVBCode)
(write-line "elseif item.damper[1].value = \"KS7L-L\" or item.damper[2].value = \"KS7L-R\" or item.damper[2].value = \"KS7L-UP\" or item.damper[2].value = \"KS7L-DN\" then" writeToVBCode)
(write-line "item.damper[1].value = \"KS7L-D2\"" writeToVBCode)
(write-line "item.damper[1].locked = true" writeToVBCode)
(write-line "end if" writeToVBCode)
(write-line "if item.damper[2].value = \"3/8\"+qt+\" ROD-L\" or item.damper[2].value = \"3/8\"+qt+\" ROD-R\" or item.damper[2].value = \"3/8\"+qt+\" ROD-UP\" or item.damper[2].value = \"3/8\"+qt+\" ROD-DN\" then" writeToVBCode)
(write-line "item.damper[2].value = \"3/8\"+qt+\" ROD-D2\"" writeToVBCode)
(write-line "item.damper[2].locked = true" writeToVBCode)
(write-line "elseif item.damper[2].value = \"KS7L-L\" or item.damper[2].value = \"KS7L-R\" or item.damper[2].value = \"KS7L-UP\" or item.damper[2].value = \"KS7L-DN\" then" writeToVBCode)
(write-line "item.damper[2].value = \"KS7L-D2\"" writeToVBCode)
(write-line "item.damper[2].locked = true" writeToVBCode)
(write-line "end if" writeToVBCode)
(write-line "if item.damper[3].value = \"3/8\"+qt+\" ROD-L\" or item.damper[3].value = \"3/8\"+qt+\" ROD-D2\" then" writeToVBCode)
(write-line "item.damper[3].value = \"3/8\"+qt+\" ROD-UP\"" writeToVBCode)
(write-line "item.damper[3].locked = true" writeToVBCode)
(write-line "elseif item.damper[3].value = \"3/8\"+qt+\" ROD-R\" then" writeToVBCode)
(write-line "item.damper[3].value = \"3/8\"+qt+\" ROD-DN\"" writeToVBCode)
(write-line "item.damper[3].locked = true" writeToVBCode)
(write-line "elseif item.damper[3].value = \"KS7L-L\" or item.damper[3].value = \"KS7L-D2\" then" writeToVBCode)
(write-line "item.damper[3].value = \"KS7L-UP\"" writeToVBCode)
(write-line "item.damper[3].locked = true" writeToVBCode)
(write-line "elseif item.damper[3].value = \"KS7L-R\" then" writeToVBCode)
(write-line "item.damper[3].value = \"KS7L-DN\"" writeToVBCode)
(write-line "item.damper[3].locked = true" writeToVBCode)
(write-line "end if" writeToVBCode)
(write-line "if item.damper[4].value = \"3/8\"+qt+\" ROD-R\" or item.damper[3].value = \"3/8\"+qt+\" ROD-D2\" then" writeToVBCode)
(write-line "item.damper[4].value = \"3/8\"+qt+\" ROD-DN\"" writeToVBCode)
(write-line "item.damper[4].locked = true" writeToVBCode)
(write-line "elseif item.damper[3].value = \"3/8\"+qt+\" ROD-L\" then" writeToVBCode)
(write-line "item.damper[4].value = \"3/8\"+qt+\" ROD-UP\"" writeToVBCode)
(write-line "item.damper[4].locked = true" writeToVBCode)
(write-line "elseif item.damper[4].value = \"KS7L-R\" or item.damper[3].value = \"KS7L-D2\" then" writeToVBCode)
(write-line "item.damper[4].value = \"KS7L-DN\"" writeToVBCode)
(write-line "item.damper[4].locked = true" writeToVBCode)
(write-line "elseif item.damper[3].value = \"KS7L-L\" then" writeToVBCode)
(write-line "item.damper[4].value = \"KS7L-UP\"" writeToVBCode)
(write-line "item.damper[4].locked = true" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (princ)
(END_ROUTINE));end defun
;**************************************************************************************************************************************************
(defun c:Switch_KS7L_to_38Rod_Damper ()
;;;; 38Rod = Switch Damper to 3/8" Rod
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.dampers > 0 then" writeToVBCode)
(write-line "if item.dampers = 1 then" writeToVBCode)
(write-line "if item.damper[1].value = \"KS7L-UP\" then" writeToVBCode)
(write-line "item.damper[1].value = \"3/8\"+qt+\" ROD-UP\"" writeToVBCode)
(write-line "item.damper[1].locked = true" writeToVBCode)
(write-line "elseif item.damper[1].value = \"KS7L-DN\" then" writeToVBCode)
(write-line "item.damper[1].value = \"3/8\"+qt+\" ROD-DN\"" writeToVBCode)
(write-line "item.damper[1].locked = true" writeToVBCode)
(write-line "end if" writeToVBCode)
(write-line "elseif item.dampers = 2 then" writeToVBCode)
(write-line "if item.damper[1].value = \"KS7L-UP\" then" writeToVBCode)
(write-line "item.damper[1].value = \"3/8\"+qt+\" ROD-UP\"" writeToVBCode)
(write-line "item.damper[1].locked = true" writeToVBCode)
(write-line "elseif item.damper[1].value = \"KS7L-DN\" then" writeToVBCode)
(write-line "item.damper[1].value = \"3/8\"+qt+\" ROD-DN\"" writeToVBCode)
(write-line "item.damper[1].locked = true" writeToVBCode)
(write-line "end if" writeToVBCode)
(write-line "if item.damper[2].value = \"KS7L-UP\" or item.damper[2].value = \"KS7L-DN\" or item.damper[2].value = \"KS7L-D2\" then" writeToVBCode)
(write-line "item.damper[2].value = \"3/8\"+qt+\" ROD-D2\"" writeToVBCode)
(write-line "item.damper[2].locked = true" writeToVBCode)
(write-line "end if" writeToVBCode)
(write-line "elseif item.dampers = 3 then" writeToVBCode)
(write-line "if item.damper[1].value = \"KS7L-UP\" then" writeToVBCode)
(write-line "item.damper[1].value = \"3/8\"+qt+\" ROD-UP\"" writeToVBCode)
(write-line "item.damper[1].locked = true" writeToVBCode)
(write-line "elseif item.damper[1].value = \"KS7L-DN\" then" writeToVBCode)
(write-line "item.damper[1].value = \"3/8\"+qt+\" ROD-DN\"" writeToVBCode)
(write-line "item.damper[1].locked = true" writeToVBCode)
(write-line "end if" writeToVBCode)
(write-line "if item.damper[2].value = \"KS7L-UP\" or item.damper[2].value = \"KS7L-DN\" or item.damper[2].value = \"KS7L-D2\" then" writeToVBCode)
(write-line "item.damper[2].value = \"3/8\"+qt+\" ROD-D2\"" writeToVBCode)
(write-line "item.damper[2].locked = true" writeToVBCode)
(write-line "end if" writeToVBCode)
(write-line "if item.damper[3].value = \"KS7L-UP\" then" writeToVBCode)
(write-line "item.damper[3].value = \"3/8\"+qt+\" ROD-UP\"" writeToVBCode)
(write-line "item.damper[3].locked = true" writeToVBCode)
(write-line "elseif item.damper[3].value = \"KS7L-DN\" then" writeToVBCode)
(write-line "item.damper[3].value = \"3/8\"+qt+\" ROD-DN\"" writeToVBCode)
(write-line "item.damper[3].locked = true" writeToVBCode)
(write-line "end if" writeToVBCode)
(write-line "elseif item.dampers = 4 then" writeToVBCode)
(write-line "if item.damper[1].value = \"KS7L-UP\" then" writeToVBCode)
(write-line "item.damper[1].value = \"3/8\"+qt+\" ROD-UP\"" writeToVBCode)
(write-line "item.damper[1].locked = true" writeToVBCode)
(write-line "elseif item.damper[1].value = \"KS7L-DN\" then" writeToVBCode)
(write-line "item.damper[1].value = \"3/8\"+qt+\" ROD-DN\"" writeToVBCode)
(write-line "item.damper[1].locked = true" writeToVBCode)
(write-line "end if" writeToVBCode)
(write-line "if item.damper[2].value = \"KS7L-UP\" or item.damper[2].value = \"KS7L-DN\" or item.damper[2].value = \"KS7L-D2\" then" writeToVBCode)
(write-line "item.damper[2].value = \"3/8\"+qt+\" ROD-D2\"" writeToVBCode)
(write-line "item.damper[2].locked = true" writeToVBCode)
(write-line "end if" writeToVBCode)
(write-line "if item.damper[3].value = \"KS7L-UP\" then" writeToVBCode)
(write-line "item.damper[3].value = \"3/8\"+qt+\" ROD-UP\"" writeToVBCode)
(write-line "item.damper[3].locked = true" writeToVBCode)
(write-line "elseif item.damper[3].value = \"KS7L-DN\" then" writeToVBCode)
(write-line "item.damper[3].value = \"3/8\"+qt+\" ROD-DN\"" writeToVBCode)
(write-line "item.damper[3].locked = true" writeToVBCode)
(write-line "end if" writeToVBCode)
(write-line "if item.damper[4].value = \"KS7L-UP\" then" writeToVBCode)
(write-line "item.damper[4].value = \"3/8\"+qt+\" ROD-UP\"" writeToVBCode)
(write-line "item.damper[4].locked = true" writeToVBCode)
(write-line "elseif item.damper[4].value = \"KS7L-DN\" then" writeToVBCode)
(write-line "item.damper[4].value = \"3/8\"+qt+\" ROD-DN\"" writeToVBCode)
(write-line "item.damper[4].locked = true" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (princ)
(END_ROUTINE));end defun
;**************************************************************************************************************************************************
(defun c:Switch_38Rod_to_KS7L_Damper ()
;;;; KS7L = Switch Damper to KS7L
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.dampers > 0 then" writeToVBCode)
(write-line "if item.dampers = 1 then" writeToVBCode)
(write-line "if item.damper[1].value = \"3/8\"+qt+\" ROD-UP\" then" writeToVBCode)
(write-line "item.damper[1].value = \"KS7L-UP\"" writeToVBCode)
(write-line "item.damper[1].locked = true" writeToVBCode)
(write-line "elseif item.damper[1].value = \"3/8\"+qt+\" ROD-DN\" then" writeToVBCode)
(write-line "item.damper[1].value = \"KS7L-DN\"" writeToVBCode)
(write-line "item.damper[1].locked = true" writeToVBCode)
(write-line "end if" writeToVBCode)
(write-line "elseif item.dampers = 2 then" writeToVBCode)
(write-line "if item.damper[1].value = \"3/8\"+qt+\" ROD-UP\" then" writeToVBCode)
(write-line "item.damper[1].value = \"KS7L-UP\"" writeToVBCode)
(write-line "item.damper[1].locked = true" writeToVBCode)
(write-line "elseif item.damper[1].value = \"3/8\"+qt+\" ROD-DN\" then" writeToVBCode)
(write-line "item.damper[1].value = \"KS7L-DN\"" writeToVBCode)
(write-line "item.damper[1].locked = true" writeToVBCode)
(write-line "end if" writeToVBCode)
(write-line "if item.damper[2].value = \"3/8\"+qt+\" ROD-UP\" or item.damper[2].value = \"3/8\"+qt+\" ROD-DN\" or item.damper[2].value = \"3/8\"+qt+\" ROD-D2\" then" writeToVBCode)
(write-line "item.damper[2].value = \"KS7L-D2\"" writeToVBCode)
(write-line "item.damper[2].locked = true" writeToVBCode)
(write-line "end if" writeToVBCode)
(write-line "elseif item.dampers = 3 then" writeToVBCode)
(write-line "if item.damper[1].value = \"3/8\"+qt+\" ROD-UP\" then" writeToVBCode)
(write-line "item.damper[1].value = \"KS7L-UP\"" writeToVBCode)
(write-line "item.damper[1].locked = true" writeToVBCode)
(write-line "elseif item.damper[1].value = \"3/8\"+qt+\" ROD-DN\" then" writeToVBCode)
(write-line "item.damper[1].value = \"KS7L-DN\"" writeToVBCode)
(write-line "item.damper[1].locked = true" writeToVBCode)
(write-line "end if" writeToVBCode)
(write-line "if item.damper[2].value = \"3/8\"+qt+\" ROD-UP\" or item.damper[2].value = \"3/8\"+qt+\" ROD-DN\" or item.damper[2].value = \"3/8\"+qt+\" ROD-D2\" then" writeToVBCode)
(write-line "item.damper[2].value = \"KS7L-D2\"" writeToVBCode)
(write-line "item.damper[2].locked = true" writeToVBCode)
(write-line "end if" writeToVBCode)
(write-line "if item.damper[3].value = \"3/8\"+qt+\" ROD-UP\" then" writeToVBCode)
(write-line "item.damper[3].value = \"KS7L-UP\"" writeToVBCode)
(write-line "item.damper[3].locked = true" writeToVBCode)
(write-line "elseif item.damper[3].value = \"3/8\"+qt+\" ROD-DN\" then" writeToVBCode)
(write-line "item.damper[3].value = \"KS7L-DN\"" writeToVBCode)
(write-line "item.damper[3].locked = true" writeToVBCode)
(write-line "end if" writeToVBCode)
(write-line "elseif item.dampers = 4 then" writeToVBCode)
(write-line "if item.damper[1].value = \"3/8\"+qt+\" ROD-UP\" then" writeToVBCode)
(write-line "item.damper[1].value = \"KS7L-UP\"" writeToVBCode)
(write-line "item.damper[1].locked = true" writeToVBCode)
(write-line "elseif item.damper[1].value = \"3/8\"+qt+\" ROD-DN\" then" writeToVBCode)
(write-line "item.damper[1].value = \"KS7L-DN\"" writeToVBCode)
(write-line "item.damper[1].locked = true" writeToVBCode)
(write-line "end if" writeToVBCode)
(write-line "if item.damper[2].value = \"3/8\"+qt+\" ROD-UP\" or item.damper[2].value = \"3/8\"+qt+\" ROD-DN\" or item.damper[2].value = \"3/8\"+qt+\" ROD-D2\" then" writeToVBCode)
(write-line "item.damper[2].value = \"KS7L-D2\"" writeToVBCode)
(write-line "item.damper[2].locked = true" writeToVBCode)
(write-line "end if" writeToVBCode)
(write-line "if item.damper[3].value = \"3/8\"+qt+\" ROD-UP\" then" writeToVBCode)
(write-line "item.damper[3].value = \"KS7L-UP\"" writeToVBCode)
(write-line "item.damper[3].locked = true" writeToVBCode)
(write-line "elseif item.damper[3].value = \"3/8\"+qt+\" ROD-DN\" then" writeToVBCode)
(write-line "item.damper[3].value = \"KS7L-DN\"" writeToVBCode)
(write-line "item.damper[3].locked = true" writeToVBCode)
(write-line "end if" writeToVBCode)
(write-line "if item.damper[4].value = \"3/8\"+qt+\" ROD-UP\" then" writeToVBCode)
(write-line "item.damper[4].value = \"KS7L-UP\"" writeToVBCode)
(write-line "item.damper[4].locked = true" writeToVBCode)
(write-line "elseif item.damper[4].value = \"3/8\"+qt+\" ROD-DN\" then" writeToVBCode)
(write-line "item.damper[4].value = \"KS7L-DN\"" writeToVBCode)
(write-line "item.damper[4].locked = true" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (princ)
(END_ROUTINE));end defun
;**************************************************************************************************************************************************
;;;; TEXT MOVE - MOVES TEXT
(defun c:Text_Move ()
  (OUTSIDE_LOOP_VARIABLES nil)
  (COMMAND "MOVETEXT")
  (prompt "Select the text you wish to move")(princ)
  (princ)
(END_ROUTINE));end defun
;**************************************************************************************************************************************************
;;;; TEXT MOVE - MOVES TEXT
(defun c:Rotate_Text ()
  (OUTSIDE_LOOP_VARIABLES nil)
  (COMMAND "ROTTEXT")
  (prompt "Select the text you wish to rotate")(princ)
  (princ)
(END_ROUTINE));end defun
;**************************************************************************************************************************************************
;| SELECT PREVIOUS - RESELECTS LAST SELECTION SET |;
(defun c:Select_Previous ()
  (OUTSIDE_LOOP_VARIABLES nil)
  (command "pselect" "p" "")
  (prompt "Last selected object has been reselected")(princ)
  (princ)
(END_ROUTINE));end defun
;**************************************************************************************************************************************************
;;;; SELECT LAST - RESELECTS LAST ENTITY ADDED TO THE DRAWING
(defun c:Select_Last_Added ()
  (OUTSIDE_LOOP_VARIABLES nil)
  (command "pselect" (entlast) "")
  (prompt "Last added object has been selected")(princ)
  (princ)
(END_ROUTINE));end defun
;**************************************************************************************************************************************************
;;;; Move Previous - Moves last selection set
(defun c:Move_Previous ()
  (OUTSIDE_LOOP_VARIABLES nil)
  (command "pselect" "p" "")
  (prompt "Ready to move last selection set")(princ)
  (command "move")
  (princ)
(END_ROUTINE));end defun
;**************************************************************************************************************************************************
;;;; Calls up a review cloud Revision_Cloud_On_Text_Layer
(defun c:Text_Cloud ()
  (OUTSIDE_LOOP_VARIABLES nil)
  (vl-load-com)
  (initcommandversion 1)
  (setq oldCurrent (getvar 'clayer))
  (command "LAYER" "SET" "M-AMC-TEXT" "")
  (initcommandversion 2)
  (setq a (getpoint "\nPick first point: ")
        b (getcorner a "\nPick other corner: "))
  (vl-cmdf "._revcloud" "_A" "3" "9" "_R" a b )
  (initcommandversion 1)
  (command "LAYER" "SET" oldCurrent "")
(END_ROUTINE));end defun
;**************************************************************************************************************************************************
(defun c:Move_X_Axis (/ sset a b)
  (OUTSIDE_LOOP_VARIABLES nil)
  (prompt "MOVE on X axis")(terpri)
  (setq sset (ssget))
  (setq a (getpoint "Select Base Point: "))(terpri)
  (setq b (getpoint a "Select Destination: "))(terpri)
  (command ".move" sset "" a ".X" b "@");change @ to pause without the quotes to manually pick direction
  (princ)
  (END_ROUTINE));end defun
;**************************************************************************************************************************************************
(defun c:Move_Y_Axis (/ sset a b)
  (OUTSIDE_LOOP_VARIABLES nil)
  (prompt "MOVE on Y axis")(terpri)
  (setq sset (ssget))
  (setq a (getpoint "Select Base Point: "))(terpri)
  (setq b (getpoint a "Select Destination: "))(terpri)
  (command ".move" sset "" a ".Y" b "@")
  (princ)
(END_ROUTINE));end defun
;**************************************************************************************************************************************************
(defun c:Move_Z_Axis (/ sset a b)
  (OUTSIDE_LOOP_VARIABLES nil)
  (prompt "MOVE on Z axis")(terpri)
  (setq sset (ssget))
  (setq a (getpoint "Select Base Point: "))(terpri)
  (setq b (getpoint a "Select Destination: "))(terpri)
  (command ".move" sset "" a ".Z" b "@")
  (princ)
(END_ROUTINE));end defun
;**************************************************************************************************************************************************
(defun c:Copy_X_Axis (/ sset a b)
  (OUTSIDE_LOOP_VARIABLES nil)
  (prompt "Copy on X axis")(terpri)
  (setq sset (ssget))
  (setq a (getpoint "Select Base Point: "))(terpri)
  (setq b (getpoint a "Select Destination: "))(terpri)
  (command ".copy" sset "" a ".X" b "@");change @ to pause without the quotes to manually pick direction
  (princ)
(END_ROUTINE));end defun
;**************************************************************************************************************************************************
(defun c:Copy_Y_Axis (/ sset a b)
  (OUTSIDE_LOOP_VARIABLES nil)
  (prompt "Copy on Y axis")(terpri)
  (setq sset (ssget))
  (setq a (getpoint "Select Base Point: "))(terpri)
  (setq b (getpoint a "Select Destination: "))(terpri)
  (command ".copy" sset "" a ".Y" b "@")
  (princ)
(END_ROUTINE));end defun
;**************************************************************************************************************************************************
(defun c:Copy_Z_Axis (/ sset a b)
  (OUTSIDE_LOOP_VARIABLES nil)
  (prompt "Copy on Z axis")(terpri)
  (setq sset (ssget))
  (setq a (getpoint "Select Base Point: "))(terpri)
  (setq b (getpoint a "Select Destination: "))(terpri)
  (command ".copy" sset "" a ".Z" b "@")
  (princ)
(END_ROUTINE));end defun
;**************************************************************************************************************************************************
(defun c:Split_View_Into_2 ()
  (OUTSIDE_LOOP_VARIABLES nil)
  (command "-vports" "2" "vertical")
  (command "view" "_SWISO")
  (command "ucs" "view")
  (princ)
(END_ROUTINE));end defun
;**************************************************************************************************************************************************
(defun c:Front_View ()
  (OUTSIDE_LOOP_VARIABLES nil)
  (command "-view" "_front")
  (command "ucs" "view")
  (princ)
(END_ROUTINE));end defun
;**************************************************************************************************************************************************
(defun c:Right_View ()
  (command "-view" "_right")
  (command "ucs" "view")
  (princ)
(END_ROUTINE));end defun
;**************************************************************************************************************************************************
(defun c:Top_View ()
  (OUTSIDE_LOOP_VARIABLES nil)
  (Command "view" "top")
  (command "ucs" "world")
  (princ)
(END_ROUTINE));end defun
;**************************************************************************************************************************************************
(defun c:Delete_All_Xclips ()
  (OUTSIDE_LOOP_VARIABLES nil)
  (command "_xclip" "all" "" "delete" ^c^c )
  (princ)
(END_ROUTINE));end defun
;**************************************************************************************************************************************************
(defun c:Import_Xref_on_Custom_Layer ( / )
  (OUTSIDE_LOOP_VARIABLES nil)
  (setq chosenFileLink (getfiled "Please select an external reference file" jobDirectory "dwg" 0))
  (if(not(= chosenFileLink nil))
    (progn
      (setq oldCurLayer (getvar "CLAYER"))
      (command "ucs" "world")
      (command "_xattach" chosenFileLink)
      (setq xrefName (strcase(cdr(assoc 2(entget(entlast))))))
      (STRING_SPLIT "\\" chosenFileLink)
      (setq folderList lst
            importLayer nil)
      (foreach el lst
        (if(wcmatch(strcase el)"*SHEET METAL*")
          (setq importLayer "3-XREF-SHMT")
          (if(wcmatch(strcase el)"*PLUMBING*")
            (setq importLayer "1-XREF-PLMB")
            (if(wcmatch(strcase el)"*MECH PIPING*")
              (setq importLayer "2-XREF-PIPE")
              (if(wcmatch(strcase el)"*XREFS*")
                (foreach elm lst
                  (if(wcmatch(strcase el)"*ARCH*")
                    (if(wcmatch xrefName "*GRID*")
                      (setq importLayer "9-XREF-GRID")
                      (setq importLayer "4-XREF-ARCH")
                    );end if
                  (if(wcmatch(strcase el)"*STRC*")
                    (setq importLayer "5-XREF-STRU")
                  (if(wcmatch(strcase el)"*ELEC*")
                    (setq importLayer "6-XREF-ELEC")
                  (if(wcmatch(strcase el)"*FIRE*")
                    (setq importLayer "7-XREF-FIRE")
                  (if(wcmatch(strcase el)"*WALL*")
                    (setq importLayer "4-XREF-ARCH")
                  (if(wcmatch(strcase el)"*CIVIL*")
                    (setq importLayer "4-XREF-ARCH")
                  (if(wcmatch(strcase el)"*PTUBE*")
                    (setq importLayer "8-XREF-USER")
                  (if(wcmatch(strcase el)"*LAB*")
                    (setq importLayer "8-XREF-USER")
                  ) ) ) ) ) ) ) );end ifs
                );foreach
        ) ) ) )
      );foreach
      (if(= importLayer nil)
        (if(or(wcmatch xrefName "*ARCH*")(wcmatch xrefName "*FLOOR*")(and(wcmatch xrefName "*ROOF*")(wcmatch xrefName "*PLAN*"))(wcmatch xrefName "*RCP*")(wcmatch xrefName "*CEILING*"))
          (progn
            (setq importLayer "4-XREF-ARCH")
            (command "-layer" "set" importLayer "lock" importLayer "")
          );progn
          (if(wcmatch xrefName "*GRID*")
            (progn
              (setq importLayer "9-XREF-GRID")
              (command "-layer" "set" importLayer "lock" importLayer "")
            );progn
            (progn
              (setq importLayer (strcat "-XREF-" xrefName))
              (command "-layer" "make" importLayer "lock" importLayer "")
            );progn
          );end if
        );end if
      );end if
      (setq update_current_layer (getvar "Clayer"))
      (setq updateXrefLayer (subst(cons 8 importLayer)(assoc 8(entget(entlast)))(entget(entlast))))
      (entmod updateXrefLayer)
      (setvar "CLAYER" oldCurLayer)
      (RESET_UCS)
    );progn
  );end if
(END_ROUTINE));end defun
;**************************************************************************************************************************************************
;;;; SELECT FIX - FIXES MAP OBJECT SELECTION SET COORDINATE LOCATIONS
(defun c:Selection_Fix ()
  (OUTSIDE_LOOP_VARIABLES nil)
  (command "move" "all" "" "0,0,0" "0,0,0")
  (prompt "Object locations have been reset.")(princ)
  (princ)
(END_ROUTINE));end defun
;**************************************************************************************************************************************************
(defun c:Multi_Dimension_Edit ()
;;;; D1 = CHOOSE VALUE FOR DIMENSION #1
(OUTSIDE_LOOP_VARIABLES nil)
(write-line "requires task.selection" writeToVBCode)
(write-line "dim i = 1" writeToVBCode)
(write-line "dim item = task.selection[i]" writeToVBCode)
(write-line "dim count = 1" writeToVBCode)
(write-line "dim limit = item.dims" writeToVBCode)
(write-line "dim qt = ASCII(34)" writeToVBCode)
(write-line "dim identity = inputbox(\"Enter dimension index #:\")" writeToVBCode)
(write-line "dim check = \"false\"" writeToVBCode)
(write-line "dim idFlag = \"invalid\"" writeToVBCode)
(write-line "while count <= limit" writeToVBCode)
(write-line "if identity = count then" writeToVBCode)
(write-line "check = \"true\"" writeToVBCode)
(write-line "idFlag = \"valid\"" writeToVBCode)
(write-line "end if" writeToVBCode)
(write-line "count = count + 1" writeToVBCode)
(write-line "end while" writeToVBCode)
(write-line "if check = \"false\" then" writeToVBCode)
(write-line "identity = qt + identity + qt" writeToVBCode)
(write-line "count = 1" writeToVBCode)
(write-line "while count <= limit" writeToVBCode)
(write-line "if (wildcard(item.dim[count].name,identity) = 1) then" writeToVBCode)
(write-line "idFlag = \"valid\"" writeToVBCode)
(write-line "end if" writeToVBCode)
(write-line "count = count + 1" writeToVBCode)
(write-line "end while" writeToVBCode)
(write-line "end if" writeToVBCode)
(write-line "if idFlag = \"valid\" then" writeToVBCode)
(write-line "if item.dim[identity].numvalue >= 0 then" writeToVBCode)
(write-line "dim self = item.dim[identity].numvalue" writeToVBCode)
(write-line "dim value = inputbox(\"Enter [VALUE]\")" writeToVBCode)
(write-line "while i <= task.selection.count" writeToVBCode)
(write-line "dim item = task.selection[i]" writeToVBCode)
(write-line "dim self = item.dim[identity].numvalue" writeToVBCode)
(write-line "dim auto = 1000000" writeToVBCode)
(write-line "dim dependent = 1100000" writeToVBCode)
(write-line "dim calc = 1100001" writeToVBCode)
(write-line "dim D1 = item.dim[1].numvalue" writeToVBCode)
(write-line "dim D2 = item.dim[2].numvalue" writeToVBCode)
(write-line "dim D3 = item.dim[3].numvalue" writeToVBCode)
(write-line "dim D4 = item.dim[4].numvalue" writeToVBCode)
(write-line "dim D5 = item.dim[5].numvalue" writeToVBCode)
(write-line "dim D6 = item.dim[6].numvalue" writeToVBCode)
(write-line "dim D7 = item.dim[7].numvalue" writeToVBCode)
(write-line "dim D8 = item.dim[8].numvalue" writeToVBCode)
(write-line "dim D9 = item.dim[9].numvalue" writeToVBCode)
(write-line "dim D10 = item.dim[10].numvalue" writeToVBCode)
(write-line "dim D11 = item.dim[11].numvalue" writeToVBCode)
(write-line "dim D12 = item.dim[12].numvalue" writeToVBCode)
(write-line "dim D13 = item.dim[13].numvalue" writeToVBCode)
(write-line "dim D14 = item.dim[14].numvalue" writeToVBCode)
(write-line "dim D15 = item.dim[15].numvalue" writeToVBCode)
(write-line "dim D16 = item.dim[16].numvalue" writeToVBCode)
(write-line "dim D17 = item.dim[17].numvalue" writeToVBCode)
(write-line "dim D18 = item.dim[18].numvalue" writeToVBCode)
(write-line "dim D19 = item.dim[19].numvalue" writeToVBCode)
(write-line "dim D20 = item.dim[20].numvalue" writeToVBCode)
(write-line "dim D21 = item.dim[21].numvalue" writeToVBCode)
(write-line "dim D22 = item.dim[22].numvalue" writeToVBCode)
(write-line "dim D23 = item.dim[23].numvalue" writeToVBCode)
(write-line "dim D24 = item.dim[24].numvalue" writeToVBCode)
(write-line "dim D25 = item.dim[25].numvalue" writeToVBCode)
(write-line "dim D26 = item.dim[26].numvalue" writeToVBCode)
(write-line "dim D27 = item.dim[27].numvalue" writeToVBCode)
(write-line "dim D28 = item.dim[28].numvalue" writeToVBCode)
(write-line "dim D29 = item.dim[29].numvalue" writeToVBCode)
(write-line "dim D30 = item.dim[30].numvalue" writeToVBCode)
(write-line "dim D31 = item.dim[31].numvalue" writeToVBCode)
(write-line "dim D32 = item.dim[32].numvalue" writeToVBCode)
(write-line "dim D33 = item.dim[33].numvalue" writeToVBCode)
(write-line "dim D34 = item.dim[34].numvalue" writeToVBCode)
(write-line "dim D35 = item.dim[35].numvalue" writeToVBCode)
(write-line "dim D36 = item.dim[36].numvalue" writeToVBCode)
(write-line "dim D37 = item.dim[37].numvalue" writeToVBCode)
(write-line "dim D38 = item.dim[38].numvalue" writeToVBCode)
(write-line "dim D39 = item.dim[39].numvalue" writeToVBCode)
(write-line "dim D40 = item.dim[40].numvalue" writeToVBCode)
(write-line "dim D41 = item.dim[41].numvalue" writeToVBCode)
(write-line "dim D42 = item.dim[42].numvalue" writeToVBCode)
(write-line "dim D43 = item.dim[43].numvalue" writeToVBCode)
(write-line "dim D44 = item.dim[44].numvalue" writeToVBCode)
(write-line "dim D45 = item.dim[45].numvalue" writeToVBCode)
(write-line "dim D46 = item.dim[46].numvalue" writeToVBCode)
(write-line "dim D47 = item.dim[47].numvalue" writeToVBCode)
(write-line "dim D48 = item.dim[48].numvalue" writeToVBCode)
(write-line "dim D49 = item.dim[49].numvalue" writeToVBCode)
(write-line "dim D50 = item.dim[50].numvalue" writeToVBCode)
(write-line "dim D51 = item.dim[51].numvalue" writeToVBCode)
(write-line "dim D52 = item.dim[52].numvalue" writeToVBCode)
(write-line "dim D53 = item.dim[53].numvalue" writeToVBCode)
(write-line "dim D54 = item.dim[54].numvalue" writeToVBCode)
(write-line "dim D55 = item.dim[55].numvalue" writeToVBCode)
(write-line "dim D56 = item.dim[56].numvalue" writeToVBCode)
(write-line "dim D57 = item.dim[57].numvalue" writeToVBCode)
(write-line "dim D58 = item.dim[58].numvalue" writeToVBCode)
(write-line "dim D59 = item.dim[59].numvalue" writeToVBCode)
(write-line "dim D60 = item.dim[60].numvalue" writeToVBCode)
(write-line "dim D61 = item.dim[61].numvalue" writeToVBCode)
(write-line "dim D62 = item.dim[62].numvalue" writeToVBCode)
(write-line "dim D63 = item.dim[63].numvalue" writeToVBCode)
(write-line "dim D64 = item.dim[64].numvalue" writeToVBCode)
(write-line "dim D65 = item.dim[65].numvalue" writeToVBCode)
(write-line "dim D66 = item.dim[66].numvalue" writeToVBCode)
(write-line "dim D67 = item.dim[67].numvalue" writeToVBCode)
(write-line "dim D68 = item.dim[68].numvalue" writeToVBCode)
(write-line "dim D69 = item.dim[69].numvalue" writeToVBCode)
(write-line "dim D70 = item.dim[70].numvalue" writeToVBCode)
(write-line "dim D71 = item.dim[71].numvalue" writeToVBCode)
(write-line "dim D72 = item.dim[72].numvalue" writeToVBCode)
(write-line "dim D73 = item.dim[73].numvalue" writeToVBCode)
(write-line "dim D74 = item.dim[74].numvalue" writeToVBCode)
(write-line "dim D75 = item.dim[75].numvalue" writeToVBCode)
(write-line "dim D76 = item.dim[76].numvalue" writeToVBCode)
(write-line "dim D77 = item.dim[77].numvalue" writeToVBCode)
(write-line "dim D78 = item.dim[78].numvalue" writeToVBCode)
(write-line "dim D79 = item.dim[79].numvalue" writeToVBCode)
(write-line "dim D80 = item.dim[80].numvalue" writeToVBCode)
(write-line "dim D81 = item.dim[81].numvalue" writeToVBCode)
(write-line "dim D82 = item.dim[82].numvalue" writeToVBCode)
(write-line "dim D83 = item.dim[83].numvalue" writeToVBCode)
(write-line "dim D84 = item.dim[84].numvalue" writeToVBCode)
(write-line "dim D85 = item.dim[85].numvalue" writeToVBCode)
(write-line "dim D86 = item.dim[86].numvalue" writeToVBCode)
(write-line "dim D87 = item.dim[87].numvalue" writeToVBCode)
(write-line "dim D88 = item.dim[88].numvalue" writeToVBCode)
(write-line "dim D89 = item.dim[89].numvalue" writeToVBCode)
(write-line "dim D90 = item.dim[90].numvalue" writeToVBCode)
(write-line "dim D91 = item.dim[91].numvalue" writeToVBCode)
(write-line "dim D92 = item.dim[92].numvalue" writeToVBCode)
(write-line "dim D93 = item.dim[93].numvalue" writeToVBCode)
(write-line "dim D94 = item.dim[94].numvalue" writeToVBCode)
(write-line "dim D95 = item.dim[95].numvalue" writeToVBCode)
(write-line "dim D96 = item.dim[96].numvalue" writeToVBCode)
(write-line "dim D97 = item.dim[97].numvalue" writeToVBCode)
(write-line "dim D98 = item.dim[98].numvalue" writeToVBCode)
(write-line "dim D99 = item.dim[99].numvalue" writeToVBCode)
(write-line "dim D100 = item.dim[100].numvalue" writeToVBCode)
(write-line "dim O1 = item.option[1].value" writeToVBCode)
(write-line "dim O2 = item.option[2].value" writeToVBCode)
(write-line "dim O3 = item.option[3].value" writeToVBCode)
(write-line "dim O4 = item.option[4].value" writeToVBCode)
(write-line "dim O5 = item.option[5].value" writeToVBCode)
(write-line "dim O6 = item.option[6].value" writeToVBCode)
(write-line "dim O7 = item.option[7].value" writeToVBCode)
(write-line "dim O8 = item.option[8].value" writeToVBCode)
(write-line "dim O9 = item.option[9].value" writeToVBCode)
(write-line "dim O10 = item.option[10].value" writeToVBCode)
(write-line "dim O11 = item.option[11].value" writeToVBCode)
(write-line "dim O12 = item.option[12].value" writeToVBCode)
(write-line "dim O13 = item.option[13].value" writeToVBCode)
(write-line "dim O14 = item.option[14].value" writeToVBCode)
(write-line "dim O15 = item.option[15].value" writeToVBCode)
(write-line "dim O16 = item.option[16].value" writeToVBCode)
(write-line "dim O17 = item.option[17].value" writeToVBCode)
(write-line "dim O18 = item.option[18].value" writeToVBCode)
(write-line "dim O19 = item.option[19].value" writeToVBCode)
(write-line "dim O20 = item.option[20].value" writeToVBCode)
(write-line "dim O21 = item.option[21].value" writeToVBCode)
(write-line "dim O22 = item.option[22].value" writeToVBCode)
(write-line "dim O23 = item.option[23].value" writeToVBCode)
(write-line "dim O24 = item.option[24].value" writeToVBCode)
(write-line "dim O25 = item.option[25].value" writeToVBCode)
(write-line "dim O26 = item.option[26].value" writeToVBCode)
(write-line "dim O27 = item.option[27].value" writeToVBCode)
(write-line "dim O28 = item.option[28].value" writeToVBCode)
(write-line "dim O29 = item.option[29].value" writeToVBCode)
(write-line "dim O30 = item.option[30].value" writeToVBCode)
(write-line "dim O31 = item.option[31].value" writeToVBCode)
(write-line "dim O32 = item.option[32].value" writeToVBCode)
(write-line "dim O33 = item.option[33].value" writeToVBCode)
(write-line "dim O34 = item.option[34].value" writeToVBCode)
(write-line "dim O35 = item.option[35].value" writeToVBCode)
(write-line "dim O36 = item.option[36].value" writeToVBCode)
(write-line "dim O37 = item.option[37].value" writeToVBCode)
(write-line "dim O38 = item.option[38].value" writeToVBCode)
(write-line "dim O39 = item.option[39].value" writeToVBCode)
(write-line "dim O40 = item.option[40].value" writeToVBCode)
(write-line "dim O41 = item.option[41].value" writeToVBCode)
(write-line "dim O42 = item.option[42].value" writeToVBCode)
(write-line "dim O43 = item.option[43].value" writeToVBCode)
(write-line "dim O44 = item.option[44].value" writeToVBCode)
(write-line "dim O45 = item.option[45].value" writeToVBCode)
(write-line "dim O46 = item.option[46].value" writeToVBCode)
(write-line "dim O47 = item.option[47].value" writeToVBCode)
(write-line "dim O48 = item.option[48].value" writeToVBCode)
(write-line "dim O49 = item.option[49].value" writeToVBCode)
(write-line "dim O50 = item.option[50].value" writeToVBCode)
(write-line "dim O51 = item.option[51].value" writeToVBCode)
(write-line "dim O52 = item.option[52].value" writeToVBCode)
(write-line "dim O53 = item.option[53].value" writeToVBCode)
(write-line "dim O54 = item.option[54].value" writeToVBCode)
(write-line "dim O55 = item.option[55].value" writeToVBCode)
(write-line "dim O56 = item.option[56].value" writeToVBCode)
(write-line "dim O57 = item.option[57].value" writeToVBCode)
(write-line "dim O58 = item.option[58].value" writeToVBCode)
(write-line "dim O59 = item.option[59].value" writeToVBCode)
(write-line "dim O60 = item.option[60].value" writeToVBCode)
(write-line "dim O61 = item.option[61].value" writeToVBCode)
(write-line "dim O62 = item.option[62].value" writeToVBCode)
(write-line "dim O63 = item.option[63].value" writeToVBCode)
(write-line "dim O64 = item.option[64].value" writeToVBCode)
(write-line "dim O65 = item.option[65].value" writeToVBCode)
(write-line "dim O66 = item.option[66].value" writeToVBCode)
(write-line "dim O67 = item.option[67].value" writeToVBCode)
(write-line "dim O68 = item.option[68].value" writeToVBCode)
(write-line "dim O69 = item.option[69].value" writeToVBCode)
(write-line "dim O70 = item.option[70].value" writeToVBCode)
(write-line "dim O71 = item.option[71].value" writeToVBCode)
(write-line "dim O72 = item.option[72].value" writeToVBCode)
(write-line "dim O73 = item.option[73].value" writeToVBCode)
(write-line "dim O74 = item.option[74].value" writeToVBCode)
(write-line "dim O75 = item.option[75].value" writeToVBCode)
(write-line "dim O76 = item.option[76].value" writeToVBCode)
(write-line "dim O77 = item.option[77].value" writeToVBCode)
(write-line "dim O78 = item.option[78].value" writeToVBCode)
(write-line "dim O79 = item.option[79].value" writeToVBCode)
(write-line "dim O80 = item.option[80].value" writeToVBCode)
(write-line "dim O81 = item.option[81].value" writeToVBCode)
(write-line "dim O82 = item.option[82].value" writeToVBCode)
(write-line "dim O83 = item.option[83].value" writeToVBCode)
(write-line "dim O84 = item.option[84].value" writeToVBCode)
(write-line "dim O85 = item.option[85].value" writeToVBCode)
(write-line "dim O86 = item.option[86].value" writeToVBCode)
(write-line "dim O87 = item.option[87].value" writeToVBCode)
(write-line "dim O88 = item.option[88].value" writeToVBCode)
(write-line "dim O89 = item.option[89].value" writeToVBCode)
(write-line "dim O90 = item.option[90].value" writeToVBCode)
(write-line "dim O91 = item.option[91].value" writeToVBCode)
(write-line "dim O92 = item.option[92].value" writeToVBCode)
(write-line "dim O93 = item.option[93].value" writeToVBCode)
(write-line "dim O94 = item.option[94].value" writeToVBCode)
(write-line "dim O95 = item.option[95].value" writeToVBCode)
(write-line "dim O96 = item.option[96].value" writeToVBCode)
(write-line "dim O97 = item.option[97].value" writeToVBCode)
(write-line "dim O98 = item.option[98].value" writeToVBCode)
(write-line "dim O99 = item.option[99].value" writeToVBCode)
(write-line "dim O100 = item.option[100].value" writeToVBCode)
(write-line "item.dim[identity].value = value" writeToVBCode)
(write-line "i = i + 1" writeToVBCode)
(write-line "end while" writeToVBCode)
(write-line "end if" writeToVBCode)
(write-line "else" writeToVBCode)
(write-line "task.message = \"Your dimension or option identification was invalid for this item.\"" writeToVBCode)
(write-line "end if" writeToVBCode)
  (close writeToVBCode)
  (Executescript vbCode)
  (vl-file-delete vbCode)
  (prompt "Your value has been applied to the item(s).")(princ)
  (princ)
(END_ROUTINE));end defun
;**************************************************************************************************************************************************
(defun c:Multi_Option_Edit ()
;;;; D2 = CHOOSE VALUE FOR DIMENSION #2
(OUTSIDE_LOOP_VARIABLES nil)
(write-line "requires task.selection" writeToVBCode)
(write-line "dim i = 1" writeToVBCode)
(write-line "dim item = task.selection[i]" writeToVBCode)
(write-line "dim count = 1" writeToVBCode)
(write-line "dim limit = item.options" writeToVBCode)
(write-line "dim qt = ASCII(34)" writeToVBCode)
(write-line "dim identity = inputbox(\"Enter option index #:\")" writeToVBCode)
(write-line "dim check = \"false\"" writeToVBCode)
(write-line "dim idFlag = \"invalid\"" writeToVBCode)
(write-line "while count <= limit" writeToVBCode)
(write-line "if identity = count then" writeToVBCode)
(write-line "check = \"true\"" writeToVBCode)
(write-line "idFlag = \"valid\"" writeToVBCode)
(write-line "end if" writeToVBCode)
(write-line "count = count + 1" writeToVBCode)
(write-line "end while" writeToVBCode)
(write-line "if check = \"false\" then" writeToVBCode)
(write-line "identity = qt + identity + qt" writeToVBCode)
(write-line "count = 1" writeToVBCode)
(write-line "while count <= limit" writeToVBCode)
(write-line "if (wildcard(item.option[count].name,identity) = 1) then" writeToVBCode)
(write-line "idFlag = \"valid\"" writeToVBCode)
(write-line "end if" writeToVBCode)
(write-line "count = count + 1" writeToVBCode)
(write-line "end while" writeToVBCode)
(write-line "end if" writeToVBCode)
(write-line "if idFlag = \"valid\" then" writeToVBCode)
(write-line "if item.option[identity].value >= 0 or item.option[identity].value < 0 then" writeToVBCode)
(write-line "dim self = item.option[identity].value" writeToVBCode)
(write-line "dim value = inputbox(\"Enter [VALUE]\")" writeToVBCode)
(write-line "while i <= task.selection.count" writeToVBCode)
(write-line "dim item = task.selection[i]" writeToVBCode)
(write-line "dim self = item.option[identity].value" writeToVBCode)
(write-line "dim auto = 1000000" writeToVBCode)
(write-line "dim dependent = 1100000" writeToVBCode)
(write-line "dim calc = 1100001" writeToVBCode)
(write-line "dim D1 = item.dim[1].numvalue" writeToVBCode)
(write-line "dim D2 = item.dim[2].numvalue" writeToVBCode)
(write-line "dim D3 = item.dim[3].numvalue" writeToVBCode)
(write-line "dim D4 = item.dim[4].numvalue" writeToVBCode)
(write-line "dim D5 = item.dim[5].numvalue" writeToVBCode)
(write-line "dim D6 = item.dim[6].numvalue" writeToVBCode)
(write-line "dim D7 = item.dim[7].numvalue" writeToVBCode)
(write-line "dim D8 = item.dim[8].numvalue" writeToVBCode)
(write-line "dim D9 = item.dim[9].numvalue" writeToVBCode)
(write-line "dim D10 = item.dim[10].numvalue" writeToVBCode)
(write-line "dim D11 = item.dim[11].numvalue" writeToVBCode)
(write-line "dim D12 = item.dim[12].numvalue" writeToVBCode)
(write-line "dim D13 = item.dim[13].numvalue" writeToVBCode)
(write-line "dim D14 = item.dim[14].numvalue" writeToVBCode)
(write-line "dim D15 = item.dim[15].numvalue" writeToVBCode)
(write-line "dim D16 = item.dim[16].numvalue" writeToVBCode)
(write-line "dim D17 = item.dim[17].numvalue" writeToVBCode)
(write-line "dim D18 = item.dim[18].numvalue" writeToVBCode)
(write-line "dim D19 = item.dim[19].numvalue" writeToVBCode)
(write-line "dim D20 = item.dim[20].numvalue" writeToVBCode)
(write-line "dim D21 = item.dim[21].numvalue" writeToVBCode)
(write-line "dim D22 = item.dim[22].numvalue" writeToVBCode)
(write-line "dim D23 = item.dim[23].numvalue" writeToVBCode)
(write-line "dim D24 = item.dim[24].numvalue" writeToVBCode)
(write-line "dim D25 = item.dim[25].numvalue" writeToVBCode)
(write-line "dim D26 = item.dim[26].numvalue" writeToVBCode)
(write-line "dim D27 = item.dim[27].numvalue" writeToVBCode)
(write-line "dim D28 = item.dim[28].numvalue" writeToVBCode)
(write-line "dim D29 = item.dim[29].numvalue" writeToVBCode)
(write-line "dim D30 = item.dim[30].numvalue" writeToVBCode)
(write-line "dim D31 = item.dim[31].numvalue" writeToVBCode)
(write-line "dim D32 = item.dim[32].numvalue" writeToVBCode)
(write-line "dim D33 = item.dim[33].numvalue" writeToVBCode)
(write-line "dim D34 = item.dim[34].numvalue" writeToVBCode)
(write-line "dim D35 = item.dim[35].numvalue" writeToVBCode)
(write-line "dim D36 = item.dim[36].numvalue" writeToVBCode)
(write-line "dim D37 = item.dim[37].numvalue" writeToVBCode)
(write-line "dim D38 = item.dim[38].numvalue" writeToVBCode)
(write-line "dim D39 = item.dim[39].numvalue" writeToVBCode)
(write-line "dim D40 = item.dim[40].numvalue" writeToVBCode)
(write-line "dim D41 = item.dim[41].numvalue" writeToVBCode)
(write-line "dim D42 = item.dim[42].numvalue" writeToVBCode)
(write-line "dim D43 = item.dim[43].numvalue" writeToVBCode)
(write-line "dim D44 = item.dim[44].numvalue" writeToVBCode)
(write-line "dim D45 = item.dim[45].numvalue" writeToVBCode)
(write-line "dim D46 = item.dim[46].numvalue" writeToVBCode)
(write-line "dim D47 = item.dim[47].numvalue" writeToVBCode)
(write-line "dim D48 = item.dim[48].numvalue" writeToVBCode)
(write-line "dim D49 = item.dim[49].numvalue" writeToVBCode)
(write-line "dim D50 = item.dim[50].numvalue" writeToVBCode)
(write-line "dim D51 = item.dim[51].numvalue" writeToVBCode)
(write-line "dim D52 = item.dim[52].numvalue" writeToVBCode)
(write-line "dim D53 = item.dim[53].numvalue" writeToVBCode)
(write-line "dim D54 = item.dim[54].numvalue" writeToVBCode)
(write-line "dim D55 = item.dim[55].numvalue" writeToVBCode)
(write-line "dim D56 = item.dim[56].numvalue" writeToVBCode)
(write-line "dim D57 = item.dim[57].numvalue" writeToVBCode)
(write-line "dim D58 = item.dim[58].numvalue" writeToVBCode)
(write-line "dim D59 = item.dim[59].numvalue" writeToVBCode)
(write-line "dim D60 = item.dim[60].numvalue" writeToVBCode)
(write-line "dim D61 = item.dim[61].numvalue" writeToVBCode)
(write-line "dim D62 = item.dim[62].numvalue" writeToVBCode)
(write-line "dim D63 = item.dim[63].numvalue" writeToVBCode)
(write-line "dim D64 = item.dim[64].numvalue" writeToVBCode)
(write-line "dim D65 = item.dim[65].numvalue" writeToVBCode)
(write-line "dim D66 = item.dim[66].numvalue" writeToVBCode)
(write-line "dim D67 = item.dim[67].numvalue" writeToVBCode)
(write-line "dim D68 = item.dim[68].numvalue" writeToVBCode)
(write-line "dim D69 = item.dim[69].numvalue" writeToVBCode)
(write-line "dim D70 = item.dim[70].numvalue" writeToVBCode)
(write-line "dim D71 = item.dim[71].numvalue" writeToVBCode)
(write-line "dim D72 = item.dim[72].numvalue" writeToVBCode)
(write-line "dim D73 = item.dim[73].numvalue" writeToVBCode)
(write-line "dim D74 = item.dim[74].numvalue" writeToVBCode)
(write-line "dim D75 = item.dim[75].numvalue" writeToVBCode)
(write-line "dim D76 = item.dim[76].numvalue" writeToVBCode)
(write-line "dim D77 = item.dim[77].numvalue" writeToVBCode)
(write-line "dim D78 = item.dim[78].numvalue" writeToVBCode)
(write-line "dim D79 = item.dim[79].numvalue" writeToVBCode)
(write-line "dim D80 = item.dim[80].numvalue" writeToVBCode)
(write-line "dim D81 = item.dim[81].numvalue" writeToVBCode)
(write-line "dim D82 = item.dim[82].numvalue" writeToVBCode)
(write-line "dim D83 = item.dim[83].numvalue" writeToVBCode)
(write-line "dim D84 = item.dim[84].numvalue" writeToVBCode)
(write-line "dim D85 = item.dim[85].numvalue" writeToVBCode)
(write-line "dim D86 = item.dim[86].numvalue" writeToVBCode)
(write-line "dim D87 = item.dim[87].numvalue" writeToVBCode)
(write-line "dim D88 = item.dim[88].numvalue" writeToVBCode)
(write-line "dim D89 = item.dim[89].numvalue" writeToVBCode)
(write-line "dim D90 = item.dim[90].numvalue" writeToVBCode)
(write-line "dim D91 = item.dim[91].numvalue" writeToVBCode)
(write-line "dim D92 = item.dim[92].numvalue" writeToVBCode)
(write-line "dim D93 = item.dim[93].numvalue" writeToVBCode)
(write-line "dim D94 = item.dim[94].numvalue" writeToVBCode)
(write-line "dim D95 = item.dim[95].numvalue" writeToVBCode)
(write-line "dim D96 = item.dim[96].numvalue" writeToVBCode)
(write-line "dim D97 = item.dim[97].numvalue" writeToVBCode)
(write-line "dim D98 = item.dim[98].numvalue" writeToVBCode)
(write-line "dim D99 = item.dim[99].numvalue" writeToVBCode)
(write-line "dim D100 = item.dim[100].numvalue" writeToVBCode)
(write-line "dim O1 = item.option[1].value" writeToVBCode)
(write-line "dim O2 = item.option[2].value" writeToVBCode)
(write-line "dim O3 = item.option[3].value" writeToVBCode)
(write-line "dim O4 = item.option[4].value" writeToVBCode)
(write-line "dim O5 = item.option[5].value" writeToVBCode)
(write-line "dim O6 = item.option[6].value" writeToVBCode)
(write-line "dim O7 = item.option[7].value" writeToVBCode)
(write-line "dim O8 = item.option[8].value" writeToVBCode)
(write-line "dim O9 = item.option[9].value" writeToVBCode)
(write-line "dim O10 = item.option[10].value" writeToVBCode)
(write-line "dim O11 = item.option[11].value" writeToVBCode)
(write-line "dim O12 = item.option[12].value" writeToVBCode)
(write-line "dim O13 = item.option[13].value" writeToVBCode)
(write-line "dim O14 = item.option[14].value" writeToVBCode)
(write-line "dim O15 = item.option[15].value" writeToVBCode)
(write-line "dim O16 = item.option[16].value" writeToVBCode)
(write-line "dim O17 = item.option[17].value" writeToVBCode)
(write-line "dim O18 = item.option[18].value" writeToVBCode)
(write-line "dim O19 = item.option[19].value" writeToVBCode)
(write-line "dim O20 = item.option[20].value" writeToVBCode)
(write-line "dim O21 = item.option[21].value" writeToVBCode)
(write-line "dim O22 = item.option[22].value" writeToVBCode)
(write-line "dim O23 = item.option[23].value" writeToVBCode)
(write-line "dim O24 = item.option[24].value" writeToVBCode)
(write-line "dim O25 = item.option[25].value" writeToVBCode)
(write-line "dim O26 = item.option[26].value" writeToVBCode)
(write-line "dim O27 = item.option[27].value" writeToVBCode)
(write-line "dim O28 = item.option[28].value" writeToVBCode)
(write-line "dim O29 = item.option[29].value" writeToVBCode)
(write-line "dim O30 = item.option[30].value" writeToVBCode)
(write-line "dim O31 = item.option[31].value" writeToVBCode)
(write-line "dim O32 = item.option[32].value" writeToVBCode)
(write-line "dim O33 = item.option[33].value" writeToVBCode)
(write-line "dim O34 = item.option[34].value" writeToVBCode)
(write-line "dim O35 = item.option[35].value" writeToVBCode)
(write-line "dim O36 = item.option[36].value" writeToVBCode)
(write-line "dim O37 = item.option[37].value" writeToVBCode)
(write-line "dim O38 = item.option[38].value" writeToVBCode)
(write-line "dim O39 = item.option[39].value" writeToVBCode)
(write-line "dim O40 = item.option[40].value" writeToVBCode)
(write-line "dim O41 = item.option[41].value" writeToVBCode)
(write-line "dim O42 = item.option[42].value" writeToVBCode)
(write-line "dim O43 = item.option[43].value" writeToVBCode)
(write-line "dim O44 = item.option[44].value" writeToVBCode)
(write-line "dim O45 = item.option[45].value" writeToVBCode)
(write-line "dim O46 = item.option[46].value" writeToVBCode)
(write-line "dim O47 = item.option[47].value" writeToVBCode)
(write-line "dim O48 = item.option[48].value" writeToVBCode)
(write-line "dim O49 = item.option[49].value" writeToVBCode)
(write-line "dim O50 = item.option[50].value" writeToVBCode)
(write-line "dim O51 = item.option[51].value" writeToVBCode)
(write-line "dim O52 = item.option[52].value" writeToVBCode)
(write-line "dim O53 = item.option[53].value" writeToVBCode)
(write-line "dim O54 = item.option[54].value" writeToVBCode)
(write-line "dim O55 = item.option[55].value" writeToVBCode)
(write-line "dim O56 = item.option[56].value" writeToVBCode)
(write-line "dim O57 = item.option[57].value" writeToVBCode)
(write-line "dim O58 = item.option[58].value" writeToVBCode)
(write-line "dim O59 = item.option[59].value" writeToVBCode)
(write-line "dim O60 = item.option[60].value" writeToVBCode)
(write-line "dim O61 = item.option[61].value" writeToVBCode)
(write-line "dim O62 = item.option[62].value" writeToVBCode)
(write-line "dim O63 = item.option[63].value" writeToVBCode)
(write-line "dim O64 = item.option[64].value" writeToVBCode)
(write-line "dim O65 = item.option[65].value" writeToVBCode)
(write-line "dim O66 = item.option[66].value" writeToVBCode)
(write-line "dim O67 = item.option[67].value" writeToVBCode)
(write-line "dim O68 = item.option[68].value" writeToVBCode)
(write-line "dim O69 = item.option[69].value" writeToVBCode)
(write-line "dim O70 = item.option[70].value" writeToVBCode)
(write-line "dim O71 = item.option[71].value" writeToVBCode)
(write-line "dim O72 = item.option[72].value" writeToVBCode)
(write-line "dim O73 = item.option[73].value" writeToVBCode)
(write-line "dim O74 = item.option[74].value" writeToVBCode)
(write-line "dim O75 = item.option[75].value" writeToVBCode)
(write-line "dim O76 = item.option[76].value" writeToVBCode)
(write-line "dim O77 = item.option[77].value" writeToVBCode)
(write-line "dim O78 = item.option[78].value" writeToVBCode)
(write-line "dim O79 = item.option[79].value" writeToVBCode)
(write-line "dim O80 = item.option[80].value" writeToVBCode)
(write-line "dim O81 = item.option[81].value" writeToVBCode)
(write-line "dim O82 = item.option[82].value" writeToVBCode)
(write-line "dim O83 = item.option[83].value" writeToVBCode)
(write-line "dim O84 = item.option[84].value" writeToVBCode)
(write-line "dim O85 = item.option[85].value" writeToVBCode)
(write-line "dim O86 = item.option[86].value" writeToVBCode)
(write-line "dim O87 = item.option[87].value" writeToVBCode)
(write-line "dim O88 = item.option[88].value" writeToVBCode)
(write-line "dim O89 = item.option[89].value" writeToVBCode)
(write-line "dim O90 = item.option[90].value" writeToVBCode)
(write-line "dim O91 = item.option[91].value" writeToVBCode)
(write-line "dim O92 = item.option[92].value" writeToVBCode)
(write-line "dim O93 = item.option[93].value" writeToVBCode)
(write-line "dim O94 = item.option[94].value" writeToVBCode)
(write-line "dim O95 = item.option[95].value" writeToVBCode)
(write-line "dim O96 = item.option[96].value" writeToVBCode)
(write-line "dim O97 = item.option[97].value" writeToVBCode)
(write-line "dim O98 = item.option[98].value" writeToVBCode)
(write-line "dim O99 = item.option[99].value" writeToVBCode)
(write-line "dim O100 = item.option[100].value" writeToVBCode)
(write-line "item.option[identity].value = value" writeToVBCode)
(write-line "i = i + 1" writeToVBCode)
(write-line "end while" writeToVBCode)
(write-line "end if" writeToVBCode)
(write-line "else" writeToVBCode)
(write-line "task.message = \"Your dimension or option identification was invalid for this item.\"" writeToVBCode)
(write-line "end if" writeToVBCode)
  (close writeToVBCode)
  (Executescript vbCode)
  (vl-file-delete vbCode)
  (prompt "Your value has been applied to the item(s).")(princ)
  (princ)
(END_ROUTINE));end defun
;**************************************************************************************************************************************************
(defun c:Fix_Cut_Type (/ sset)
;;;; FCT = Fix Cut Types
(setq sset (ssget "_X" '((0 . "MAPS_SOLID"))));Auto choose selection set
(OUTSIDE_LOOP_VARIABLES nil)
(write-line "select item.CID" writeToVBCode)
(write-line "case 40" writeToVBCode)
(write-line "item.cuttype = \"Spiral Straight\"" writeToVBCode)
(write-line "case 866" writeToVBCode)
(write-line "if item.dim[\"Length\"].value < 56 or item.dim[\"Width\"].value < 1.5 or item.dim[\"Depth\"].value < 1.5 or item.dim[\"Width\"].value > 124 or item.dim[\"Depth\"].value > 124 then" writeToVBCode)
(write-line "item.cuttype = \"Machine Cut\"" writeToVBCode)
(write-line "else" writeToVBCode)
(write-line "item.cuttype = \"Decoiled Straight\"" writeToVBCode)
(write-line "end if" writeToVBCode)
(write-line "case 166,514,523,555,873,838,910,521,996,505,530,535,580,504,5231,3" writeToVBCode)
(write-line "item.cuttype = \"Equipment\"" writeToVBCode)
(write-line "case 7,20,8,2,330,54,53,807,812,1,17,30,382,861,19,61,818,51,875,751,16,345,51,818,162,68,60,64,31,388,856,5000,382,12,802" writeToVBCode)
(write-line "item.cuttype = \"Machine Cut\"" writeToVBCode)
(write-line "case 522" writeToVBCode)
(write-line "if item.description = \"#2 RND. CPLG. PIPE\" then" writeToVBCode)
(write-line "item.cuttype = \"Draw Only\"" writeToVBCode)
(write-line "else" writeToVBCode)
(write-line "item.cuttype = \"Equipment\"" writeToVBCode)
(write-line "end if" writeToVBCode)
(write-line "case 902" writeToVBCode)
(write-line "if item.description = \"Access Zone\" then" writeToVBCode)
(write-line "item.cuttype = \"Draw Only\"" writeToVBCode)
(write-line "else" writeToVBCode)
(write-line "item.cuttype = \"Equipment\"" writeToVBCode)
(write-line "end if" writeToVBCode)
(write-line "end select" writeToVBCode)
  (close writeToVBCode)
  (command "pselect" sset "")
  (Executescript vbCode)
  (vl-file-delete vbCode)
  (prompt "All instantiated library cut types have been corrected per standards.")(princ)
  
  (princ)
(END_ROUTINE));end defun
;**************************************************************************************************************************************************
(defun c:Fix_Round_Straight_Connectors (/ sset)
;;;; FRSC = Fix Round Straight Connectors
(setq sset (ssget "_X" '((0 . "MAPS_SOLID"))));Auto choose selection set
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.CID = 40 then" writeToVBCode)
(write-line "dim c1Num = 1" writeToVBCode)
(write-line "dim c1Name = \"Raw\"" writeToVBCode)
(write-line "dim c1Grp = \"Round Duct\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "dim c2Num = 2" writeToVBCode)
(write-line "dim c2Name = \"Raw\"" writeToVBCode)
(write-line "dim c2Grp = \"Round Duct\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c2Num].value = c1Name" writeToVBCode)
(write-line "item.connector[c2Num].locked = true" writeToVBCode)
(write-line "if item.connector[c2Num].group <> c1Grp then" writeToVBCode)
(write-line "connFind(c2Num,c2Grp,c2Name)" writeToVBCode)
(write-line "end if" writeToVBCode)
(write-line "end if" writeToVBCode)
(write-line "i = i + 1" writeToVBCode)
(write-line "end while" writeToVBCode)
  (close writeToVBCode)
  (command "pselect" sset "")
  (Executescript vbCode)
  (vl-file-delete vbCode)
  (prompt "All instantiated round straight connectors have been locked to RAW per standards.")(princ)
  
  (princ)
(END_ROUTINE));end defun
;**************************************************************************************************************************************************
(defun c:FIX_LENGTHS ()
  (setq i 0
        sset (ssget "X" '((0 . "MAPS_SOLID"))));end setq
  (OUTSIDE_LOOP_VARIABLES sset)
  (close writeToVBCode)
  (vl-file-delete vbCode)
  (while(< i limit)
    (INSIDE_LOOP_VARIABLES sset i)
    (if(and(/= ItemLengthAngle 0)
       (or(wcmatch ItemSourceFileName "*SPIRAL")
          (wcmatch ItemSourceFileName "Tube")
          (wcmatch ItemSourceFileName "STRAIGHT")
          (wcmatch ItemSourceFileName "Straight")
          (wcmatch ItemSourceFileName "OGEE")
          (wcmatch ItemSourceFileName "TRANSITION")
          (wcmatch ItemSourceFileName "Transition")
          (wcmatch ItemSourceFileName "F 41")
          (wcmatch ItemSourceFileName "SQ-RD")
          (wcmatch ItemSourceFileName "Square to Round")
          (wcmatch ItemSourceFileName "Mitered Offset Fixed")))
      (progn
        (setq roundedItemLengthAngle (ROUND ItemLengthAngle 1))
        (if(and(/= roundedItemLengthAngle 0)(/= roundedItemLengthAngle ItemLengthAngle))
          (progn
            (OUTSIDE_LOOP_VARIABLES sset)
            (write-line (strcat "item.dim[\"Length\"].value = " (rtos roundedItemLengthAngle 2)) writeToVBCode)
            (close writeToVBCode)
            (executescript vbCode SSentity)
            (vl-file-delete vbCode)
          );end progn
        );end if
      );end progn
    );end if
        (setq i (1+ i))
  );end while
  (princ)
(END_ROUTINE));end defun
;**************************************************************************************************************************************************
(defun c:Fix_Download ()
  (c:Fix_Cut_Type)
  (c:Fix_Round_Straight_Connectors)
(END_ROUTINE));end defun
;**************************************************************************************************************************************************
(defun c:Flip ()
  ;;;; FLIP = FLIP THE ITEM AROUND THE CHOSEN OPENING'S AXIS
  (prompt "Apply the attacher arrow to the opening axis that you want to flip around.")(princ)
  (command "._attacher" pause "")
  (command "._rotateatend" "180" "")
  (command "._attachoff")
  (prompt "Item was flipped around the center axis of the chosen opening.")(princ)
  (princ)
(END_ROUTINE));end defun
;**************************************************************************************************************************************************
(defun c:Rotate_FSD_Motor () 
  ;;;; 90 = ROTATE AROUND ARROW (3D R0TATE USING ATTACHER) - WILL ROTATE AT POSITIVE 90 DEGREE INCREMENTS AROUND THE CONNECTOR AXIS OF THE SELECTED OPENING
  (command "._attacher" pause "")
  (command "._rotateatend" "90" "")
  (command "._attachoff")
(OUTSIDE_LOOP_VARIABLES nil)
(write-line "if (wildcard(item.dim[1].name,\"Width\") = 1) and (wildcard(item.dim[2].name,\"Depth\") = 1) then" writeToVBCode)
(write-line "dim oldWidth = item.dim[1].value" writeToVBCode)
(write-line "dim oldDepth = item.dim[2].value" writeToVBCode)
(write-line "item.dim[1].value = oldDepth" writeToVBCode)
(write-line "item.dim[2].value = oldWidth" writeToVBCode)
(write-line "end if" writeToVBCode)
  (close writeToVBCode)
  (command "pselect" "p" "")
  (Executescript vbCode)
  (vl-file-delete vbCode)
(princ)
(END_ROUTINE));end defun
;**************************************************************************************************************************************************
(defun c:Rotate_Around_Attacher () 
  ;;;; RA = ROTATE AROUND ARROW (3D R0TATE USING ATTACHER) - WILL ROTATE AT POSITIVE USER INPUT DEGREE AROUND THE CONNECTOR AXIS OF THE SELECTED OPENING
  (command "._attacher" pause "")
  (command "._rotateatend" pause "")
  (command "._attachoff")
(princ)
(END_ROUTINE));end defun
;**************************************************************************************************************************************************
(defun c:Toggle_Grille ()
;;;; TG = TOGGLE GRILLE - WILL TOGGLE NECESSARY ADJUSTMENTS TO MODEL TAPS AS GRILLES
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.CID = 818 then" writeToVBCode)
(write-line "if item.connector[3].value <> \"1 Flg In\" then" writeToVBCode)
(write-line "item.dim[\"Branch Width #1\"].value = item.dim[\"Branch Width #1\"].value + 2" writeToVBCode)
(write-line "item.dim[\"Branch Depth #1\"].value = item.dim[\"Branch Depth #1\"].value + 2" writeToVBCode)
(write-line "item.dim[\"Branch Length #1\"].value = item.dim[\"Branch Length #1\"].value - item.dim[\"Branch Length #1\"].value + 13" writeToVBCode)
(write-line "item.dim[\"Branch Extension #1\"].value = item.dim[\"Branch Extension #1\"].value - item.dim[\"Branch Extension #1\"].value + 9" writeToVBCode)
(write-line "item.damper[3].value = \"RECT DAMPER-R\"" writeToVBCode)
(write-line "item.damper[3].locked = true" writeToVBCode)
(write-line "item.update()" writeToVBCode)
(write-line "REM ==== BEGIN GRILLE FUNCTION ====" writeToVBCode)
(write-line "dim c1Num = 3" writeToVBCode)
(write-line "dim c1Name = \"1 Flg In\"" writeToVBCode)
(write-line "dim c1Grp = \"Duct - Flanged\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END GRILLE FUNCTION ====" writeToVBCode)
(write-line "elseif item.connector[3].value = \"1 Flg In\" then" writeToVBCode)
(write-line "item.dim[\"Branch Width #1\"].value = item.dim[\"Branch Width #1\"].value - 2" writeToVBCode)
(write-line "item.dim[\"Branch Depth #1\"].value = item.dim[\"Branch Depth #1\"].value - 2" writeToVBCode)
(write-line "item.dim[\"Branch Length #1\"].value = item.dim[\"Branch Length #1\"].value - item.dim[\"Branch Length #1\"].value + 6" writeToVBCode)
(write-line "item.dim[\"Branch Extension #1\"].value = item.dim[\"Branch Extension #1\"].value - item.dim[\"Branch Extension #1\"].value + 0" writeToVBCode)
(write-line "item.damper[3].value = \"NONE\"" writeToVBCode)
(write-line "item.damper[3].locked = true" writeToVBCode)
(write-line "item.update()" writeToVBCode)
(write-line "if (((wildcard(item.service, \"*1/2\"+qt+\"*\") = 1) and ((item.dim[2].value > 36 or item.dim[3].value > 36) or (item.dim[2].value > 18 and item.dim[3].value > 18)))" writeToVBCode)
(write-line "or ((wildcard(item.service, \"*1\"+qt+\"*\") = 1) and ((item.dim[2].value > 36 or item.dim[3].value > 36) or (item.dim[2].value > 18 and item.dim[3].value > 18)))" writeToVBCode)
(write-line "or ((wildcard(item.service, \"*2\"+qt+\"*\") = 1) and ((item.dim[2].value > 26 or item.dim[3].value > 26) or (item.dim[2].value > 18 and item.dim[3].value > 18)))" writeToVBCode)
(write-line "or ((wildcard(item.service, \"*3\"+qt+\"*\") = 1) and ((item.dim[2].value > 22 or item.dim[3].value > 22) or (item.dim[2].value > 18 and item.dim[3].value > 18)))" writeToVBCode)
(write-line "or ((wildcard(item.service, \"*4\"+qt+\"*\") = 1) and ((item.dim[2].value > 22 or item.dim[3].value > 22) or (item.dim[2].value > 18 and item.dim[3].value > 18)))" writeToVBCode)
(write-line "or ((wildcard(item.service, \"*6\"+qt+\"*\") = 1) and (item.dim[2].value > 0 or item.dim[3].value > 0))" writeToVBCode)
(write-line "or ((wildcard(item.service, \"*10\"+qt+\"*\") = 1) and (item.dim[2].value > 0 or item.dim[3].value > 0))) then" writeToVBCode)
(write-line "REM ==== BEGIN TDF FUNCTION ====" writeToVBCode)
(write-line "dim c1Num = 3" writeToVBCode)
(write-line "dim c1Name = \"TDF \"" writeToVBCode)
(write-line "dim c1Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END TDF FUNCTION ====" writeToVBCode)
(write-line "item.update()" writeToVBCode)
(write-line "elseif (((wildcard(item.service, \"*1/2\"+qt+\"*\") = 1) and (((item.dim[2].value <= 36 and item.dim[2].value >= 21) and item.dim[3].value <= 18) or ((item.dim[3].value <= 36 and item.dim[3].value >= 21) and item.dim[2].value <= 18)))" writeToVBCode)
(write-line "or ((wildcard(item.service, \"*1\"+qt+\"*\") = 1) and (((item.dim[2].value <= 36 and item.dim[2].value >= 21) and item.dim[3].value <= 18) or ((item.dim[3].value <= 36 and item.dim[3].value >= 21) and item.dim[2].value <= 18)))" writeToVBCode)
(write-line "or ((wildcard(item.service, \"*2\"+qt+\"*\") = 1) and (((item.dim[2].value <= 26 and item.dim[2].value >= 17) and item.dim[3].value <= 18) or ((item.dim[3].value <= 26 and item.dim[3].value >= 17) and item.dim[2].value <= 18)))" writeToVBCode)
(write-line "or ((wildcard(item.service, \"*3\"+qt+\"*\") = 1) and (((item.dim[2].value <= 22 and item.dim[2].value >= 17) and item.dim[3].value <= 18) or ((item.dim[3].value <= 22 and item.dim[3].value >= 17) and item.dim[2].value <= 18)))" writeToVBCode)
(write-line "or ((wildcard(item.service, \"*4\"+qt+\"*\") = 1) and (((item.dim[2].value <= 22 and item.dim[2].value >= 17) and item.dim[3].value <= 18) or ((item.dim[3].value <= 22 and item.dim[3].value >= 17) and item.dim[2].value <= 18)))) then" writeToVBCode)
(write-line "REM ==== BEGIN STAND S&D FUNCTION ====" writeToVBCode)
(write-line "dim c1Num = 3" writeToVBCode)
(write-line "dim c1Name = \"Stand S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END STAND S&D FUNCTION ====" writeToVBCode)
(write-line "item.update()" writeToVBCode)
(write-line "elseif (((wildcard(item.service, \"*1/2\"+qt+\"*\") = 1) and (item.dim[2].value < 21 and item.dim[3].value < 21))" writeToVBCode)
(write-line "or ((wildcard(item.service, \"*1\"+qt+\"*\") = 1) and (item.dim[2].value < 21 and item.dim[3].value < 21))" writeToVBCode)
(write-line "or ((wildcard(item.service, \"*2\"+qt+\"*\") = 1) and (item.dim[2].value < 17 and item.dim[3].value < 17))" writeToVBCode)
(write-line "or ((wildcard(item.service, \"*3\"+qt+\"*\") = 1) and (item.dim[2].value < 17 and item.dim[3].value < 17))" writeToVBCode)
(write-line "or ((wildcard(item.service, \"*4\"+qt+\"*\") = 1) and (item.dim[2].value < 17 and item.dim[3].value < 17))) then" writeToVBCode)
(write-line "REM ==== BEGIN FLAT S&D FUNCTION ====" writeToVBCode)
(write-line "dim c1Num = 3" writeToVBCode)
(write-line "dim c1Name = \"Flat S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END FLAT S&D FUNCTION ====" writeToVBCode)
(write-line "item.update()" writeToVBCode)
(write-line "end if" writeToVBCode)
(write-line "end if" writeToVBCode)
(write-line "elseif item.CID = 7 then" writeToVBCode)
(write-line "if item.connector[1].value <> \"1 Flg In\" then" writeToVBCode)
(write-line "item.dim[1].value = item.dim[1].value + 2" writeToVBCode)
(write-line "item.dim[2].value = item.dim[2].value + 2" writeToVBCode)
(write-line "item.dim[3].value = item.dim[3].numvalue - item.dim[3].numvalue + 13" writeToVBCode)
(write-line "item.dim[4].value = item.dim[4].value - item.dim[4].value + 9" writeToVBCode)
(write-line "item.damper[1].value = \"RECT DAMPER-R\"" writeToVBCode)
(write-line "item.damper[1].locked = true" writeToVBCode)
(write-line "item.update()" writeToVBCode)
(write-line "REM ==== BEGIN GRILLE FUNCTION ====" writeToVBCode)
(write-line "dim c1Num = 1" writeToVBCode)
(write-line "dim c1Name = \"1 Flg In\"" writeToVBCode)
(write-line "dim c1Grp = \"Duct - Flanged\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END GRILLE FUNCTION ====" writeToVBCode)
(write-line "elseif item.connector[1].value = \"1 Flg In\" then" writeToVBCode)
(write-line "item.dim[1].value = item.dim[1].value - 2" writeToVBCode)
(write-line "item.dim[2].value = item.dim[2].value - 2" writeToVBCode)
(write-line "item.dim[3].value = item.dim[3].numvalue - item.dim[3].numvalue + 6" writeToVBCode)
(write-line "item.dim[4].value = item.dim[4].value - item.dim[4].value + 1.5" writeToVBCode)
(write-line "item.damper[1].value = \"NONE\"" writeToVBCode)
(write-line "item.damper[1].locked = true" writeToVBCode)
(write-line "item.update()" writeToVBCode)
(write-line "if (((wildcard(item.service, \"*1/2\"+qt+\"*\") = 1) and ((item.dim[1].value > 36 or item.dim[2].value > 36) or (item.dim[1].value > 18 and item.dim[2].value > 18)))" writeToVBCode)
(write-line "or ((wildcard(item.service, \"*1\"+qt+\"*\") = 1) and ((item.dim[1].value > 36 or item.dim[2].value > 36) or (item.dim[1].value > 18 and item.dim[2].value > 18)))" writeToVBCode)
(write-line "or ((wildcard(item.service, \"*2\"+qt+\"*\") = 1) and ((item.dim[1].value > 26 or item.dim[2].value > 26) or (item.dim[1].value > 18 and item.dim[2].value > 18)))" writeToVBCode)
(write-line "or ((wildcard(item.service, \"*3\"+qt+\"*\") = 1) and ((item.dim[1].value > 22 or item.dim[2].value > 22) or (item.dim[1].value > 18 and item.dim[2].value > 18)))" writeToVBCode)
(write-line "or ((wildcard(item.service, \"*4\"+qt+\"*\") = 1) and ((item.dim[1].value > 22 or item.dim[2].value > 22) or (item.dim[1].value > 18 and item.dim[2].value > 18)))" writeToVBCode)
(write-line "or ((wildcard(item.service, \"*6\"+qt+\"*\") = 1) and (item.dim[1].value > 0 or item.dim[2].value > 0))" writeToVBCode)
(write-line "or ((wildcard(item.service, \"*10\"+qt+\"*\") = 1) and (item.dim[1].value > 0 or item.dim[2].value > 0))) then" writeToVBCode)
(write-line "REM ==== BEGIN TDF FUNCTION ====" writeToVBCode)
(write-line "dim c1Num = 1" writeToVBCode)
(write-line "dim c1Name = \"TDF \"" writeToVBCode)
(write-line "dim c1Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END TDF FUNCTION ====" writeToVBCode)
(write-line "item.update()" writeToVBCode)
(write-line "elseif (((wildcard(item.service, \"*1/2\"+qt+\"*\") = 1) and (((item.dim[1].value <= 36 and item.dim[1].value >= 21) and item.dim[2].value <= 18) or ((item.dim[2].value <= 36 and item.dim[2].value >= 21) and item.dim[1].value <= 18)))" writeToVBCode)
(write-line "or ((wildcard(item.service, \"*1\"+qt+\"*\") = 1) and (((item.dim[1].value <= 36 and item.dim[1].value >= 21) and item.dim[2].value <= 18) or ((item.dim[2].value <= 36 and item.dim[2].value >= 21) and item.dim[1].value <= 18)))" writeToVBCode)
(write-line "or ((wildcard(item.service, \"*2\"+qt+\"*\") = 1) and (((item.dim[1].value <= 26 and item.dim[1].value >= 17) and item.dim[2].value <= 18) or ((item.dim[2].value <= 26 and item.dim[2].value >= 17) and item.dim[1].value <= 18)))" writeToVBCode)
(write-line "or ((wildcard(item.service, \"*3\"+qt+\"*\") = 1) and (((item.dim[1].value <= 22 and item.dim[1].value >= 17) and item.dim[2].value <= 18) or ((item.dim[2].value <= 22 and item.dim[2].value >= 17) and item.dim[1].value <= 18)))" writeToVBCode)
(write-line "or ((wildcard(item.service, \"*4\"+qt+\"*\") = 1) and (((item.dim[1].value <= 22 and item.dim[1].value >= 17) and item.dim[2].value <= 18) or ((item.dim[2].value <= 22 and item.dim[2].value >= 17) and item.dim[1].value <= 18)))) then" writeToVBCode)
(write-line "REM ==== BEGIN STAND S&D FUNCTION ====" writeToVBCode)
(write-line "dim c1Num = 1" writeToVBCode)
(write-line "dim c1Name = \"Stand S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END STAND S&D FUNCTION ====" writeToVBCode)
(write-line "item.update()" writeToVBCode)
(write-line "elseif (((wildcard(item.service, \"*1/2\"+qt+\"*\") = 1) and (item.dim[1].value < 21 and item.dim[2].value < 21))" writeToVBCode)
(write-line "or ((wildcard(item.service, \"*1\"+qt+\"*\") = 1) and (item.dim[1].value < 21 and item.dim[2].value < 21))" writeToVBCode)
(write-line "or ((wildcard(item.service, \"*2\"+qt+\"*\") = 1) and (item.dim[1].value < 17 and item.dim[2].value < 17))" writeToVBCode)
(write-line "or ((wildcard(item.service, \"*3\"+qt+\"*\") = 1) and (item.dim[1].value < 17 and item.dim[2].value < 17))" writeToVBCode)
(write-line "or ((wildcard(item.service, \"*4\"+qt+\"*\") = 1) and (item.dim[1].value < 17 and item.dim[2].value < 17))) then" writeToVBCode)
(write-line "REM ==== BEGIN FLAT S&D FUNCTION ====" writeToVBCode)
(write-line "dim c1Num = 1" writeToVBCode)
(write-line "dim c1Name = \"Flat S&D\"" writeToVBCode)
(write-line "dim c1Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "REM ==== END FLAT S&D FUNCTION ====" writeToVBCode)
(write-line "item.update()" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (princ)
(END_ROUTINE));end defun
;**************************************************************************************************************************************************
(defun c:Add_Grille ()
  ;;;; AG = ADD GRILLE - ADDS GRILLE TO SELECTED OPENING
  (command "._attacher" pause "")
  (command (takeoff Grille))
  (command "._attachoff")
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.CID = 505 then" writeToVBCode)
(write-line "item.dim[1].value = item.dim[1].value - 2" writeToVBCode)
(write-line "item.dim[2].value = item.dim[2].value - 2" writeToVBCode)
(write-line "item.update()" writeToVBCode)
(write-line "end if" writeToVBCode)
(write-line "i = i + 1" writeToVBCode)
(write-line "end while" writeToVBCode)
  (close writeToVBCode)
  (command "pselect" (entlast) "")
  (Executescript vbCode)
  (vl-file-delete vbCode)
  (command "._attachoff")
(princ)
(END_ROUTINE));end defun
;**************************************************************************************************************************************************
(defun c:Paste_To_Original_Coordinates () 
  ;;;; PO = PASTE ORIGINAL - PASTE CLIPBOARD TO ORIGINAL COORDINATES
  (command "._pasteorig")
(princ)
(END_ROUTINE));end defun
;**************************************************************************************************************************************************
(defun c:Improved_Section_View ( / a b) 
  ;;;; SV = SECTION VIEW - PICK YOUR SECTION CUT
  (*push-error-using-command*)
  (defun tempError ( msg )
    (if(and(not(= Pt1 nil))(not(= Pt2 nil)))
      (progn
        (command-s "sectional" Pt1 Pt2)
        (setq sset (ssget "X" '((0 . "MAPS_SOLID"))));end setq
        (command-s "._zoom" "object" sset "")
        (command-s "ucs" "view")
        (princ "Standard sectional command utilized after error")
      );end progn
    );end ifs
    (setvar 'osmode oldOSMode)
    (setvar 'autosnap oldAutoSnap)
    (setvar 'orthomode oldOrthoMode)
    (setq *ERROR* oldError
          oldError nil)
    (command-s)(command-s)
    (princ) 
  );end defun
  (OUTSIDE_LOOP_VARIABLES nil)
  (if(= UCSName "Unnamed")(progn(terpri)(princ "Warning: You are in an unnamed USC, double check your viewcube to confirm UCS orientation")(terpri)))
  (setq oldError *ERROR*
        *ERROR* tempError
        oldOSMode (getvar "osmode")
        oldAutoSnap (getvar "autosnap")
        oldOrthoMode (getvar "orthomode"));end setq
  (setvar 'orthomode 0)
  (setvar 'osmode 16384)
  (setvar 'autosnap 47)
  (setvar 'osnapz 0)
  (setq Pt1 nil
        Pt2 nil
        Pt1 (getpoint "\nPick first point: ")
        Pt2 (getpoint Pt1 "\nPick second point: "))
  (setq sset (ssget "_C" Pt1 Pt2 '((0 . "MAPS_SOLID"))))
  (if(not(= sset nil))
    (progn
      (setq i (if(>=(-(sslength sset)1)0)(-(sslength sset)1)(sslength sset)));end setq / if
      (INSIDE_LOOP_VARIABLES sset i)
      (command "SECTIONAL" Pt1 Pt2)
      (command "UCS" "W")
      (command "UCS" "VIEW")
      (command "CAL" "ucsC1xyz=w2u(c1xyz)")
      (command "UCS" "M" (strcat(rtos(car ucsC1xyz)2) "," (rtos(cadr ucsC1xyz)2) "," (rtos(caddr ucsC1xyz)2)))
      (command "CAL" "ucsC1xyz=w2u(c1xyz)")
      (command "._zoom" "object" sset "")
      (princ)
    );end progn
    (progn
      (command "sectional" Pt1 Pt2)
      (setq sset (ssget "X" '((0 . "MAPS_SOLID"))));end setq
      (command "._zoom" "object" sset "")
      (command "ucs" "view")
      (princ "Standard sectional command utilized")
      (princ)
    );end progn
  );end if
  (setvar 'osmode oldOSMode)
  (setvar 'autosnap oldAutoSnap)
  (setvar 'orthomode oldOrthoMode)
  (setq *ERROR* oldError)
  (princ)
(END_ROUTINE));end defun
;**************************************************************************************************************************************************
(defun c:Last_View () 
  ;;;; LV = LAST VIEW - ROLL BACK TO LAST VIEW (BEFORE SECTION CUT)
  (command "LASTVIEW")
  (RESET_UCS)
  ;(command "ucs" "p")
  (princ)
(END_ROUTINE));end defun
;**************************************************************************************************************************************************
(defun c:Last_View_WCS () 
  ;;;; LV = LAST VIEW - ROLL BACK TO LAST VIEW (BEFORE SECTION CUT)
  (command "LASTVIEW")
  (command "ucs" "w")
  (princ)
(END_ROUTINE));end defun
;**************************************************************************************************************************************************
(defun c:World_View () 
  ;;;; WV = WORLD VIEW - BACK TO WORLD VIEW (BEFORE SECTION CUT)
  (command "ucs" "world")
  (command "planview")(command)
  (princ)
(END_ROUTINE));end defun
;**************************************************************************************************************************************************
(defun c:Fix_Variables () 
  (setvar 'filetabpreview 0)
  (setvar 'filetabthumbhover 0)
  (setvar 'msltscale 0)
  (setvar 'psltscale 0)
  (setvar 'celtscale 1)
  (setvar 'ltscale 48)
  (setvar 'cmdecho 1)
  (setvar 'lwdisplay 0)
  (setvar 'selectionannodisplay 0)
  (setvar 'annoallvisible 1)
  (setvar 'annoautoscale 1)
  (if(and(not(=(getvar 'dimscale)0))(not(=(getvar 'dimscale)48)))(setvar 'dimscale 48))
  (setvar 'layernotify 0)
  (setvar 'layerevalctl 0)
  (setvar 'filedia 1)
  (setvar 'proxygraphics 1)
  (setvar 'proxynotice 0)
  (setvar 'proxyshow 1)
  (setvar 'visretain 1)
  (setvar 'cecolor "bylayer")
  (princ)
(END_ROUTINE));end defun
;**************************************************************************************************************************************************
(defun c:Toggle_Dimside () 
;;;; TD = TOGGLE DIMSIDE - SWITCH BETWEEN READING DIMS INSIDE/OUTSIDE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.dimside = \"outside\" then" writeToVBCode)
(write-line "item.dimside = \"inside\"" writeToVBCode)
(write-line "elseif item.dimside = \"inside\" then" writeToVBCode)
(write-line "item.dimside = \"outside\"" writeToVBCode)
(write-line "end if" writeToVBCode)
(write-line "i = i + 1" writeToVBCode)
(write-line "end while" writeToVBCode)
  (close writeToVBCode)
  (Executescript vbCode)
  (vl-file-delete vbCode)
  (princ)
(END_ROUTINE));end defun
;**************************************************************************************************************************************************
(defun c:Toggle_Clearance_Zone () 
  ;;;; c:TNF-Toggle_No-Fly_Zone - WRAP DUCT WITH A NO-FLY ZONE
(OUTSIDE_LOOP_VARIABLES nil)
(write-line "requires task.selection" writeToVBCode)
(write-line "dim i = 1" writeToVBCode)
(write-line "dim qt = ASCII(34)" writeToVBCode)
(write-line "dim item = task.selection[i]" writeToVBCode)
(write-line "if item.doublewall = false then" writeToVBCode)
(write-line "dim zoneThickness = inputbox(\"No-Fly Zone Thickness:\")" writeToVBCode)
(write-line "while i <= task.selection.count" writeToVBCode)
(write-line "dim item = task.selection[i]" writeToVBCode)
(write-line "item.ispeclock = false" writeToVBCode)
(write-line "item.insspec = \"None\"" writeToVBCode)
(write-line "item.ispeclock = true" writeToVBCode)
(write-line "item.dwlock = false" writeToVBCode)
(write-line "item.doublewall = true" writeToVBCode)
(write-line "item.dwlock = true" writeToVBCode)
(write-line "item.update()" writeToVBCode)
(write-line "item.skinmateriallock = false" writeToVBCode)
(write-line "item.skinmaterial = \"Ductwork No-Fly Zone\"" writeToVBCode)
(write-line "item.skinmateriallock = true" writeToVBCode)
(write-line "item.insulation.status = \"OUTSIDE\"" writeToVBCode)
(write-line "item.insulation.materiallock = false" writeToVBCode)
(write-line "item.insulation.material = \"Ductwork No-Fly Zone: Ductwork No-Fly Zone\"" writeToVBCode)
(write-line "item.insulation.materiallock = true" writeToVBCode)
(write-line "item.insulation.gauge = zoneThickness" writeToVBCode)
(write-line "item.dimsidelock = false" writeToVBCode)
(write-line "item.dimside = \"inside\"" writeToVBCode)
(write-line "item.dimsidelock = true" writeToVBCode)
(write-line "item.skinside = \"outside\"" writeToVBCode)
(write-line "item.update()" writeToVBCode)
(write-line "i = i + 1" writeToVBCode)
(write-line "end while" writeToVBCode)
(write-line "elseif item.doublewall = true then" writeToVBCode)
(write-line "dim insulationType = inputbox(\"Type:HVAC[Liner]/Duct[Wrap]/[Off]/[Fire]Barrier?:\")" writeToVBCode)
(write-line "if insulationType = \"Off\" or insulationType = \"off\" or insulationType = \"OFF\" then" writeToVBCode)
(write-line "while i <= task.selection.count" writeToVBCode)
(write-line "dim item = task.selection[i]" writeToVBCode)
(write-line "dim insulStatus = \"OFF\"" writeToVBCode)
(write-line "item.dwlock = false" writeToVBCode)
(write-line "item.doublewall = false" writeToVBCode)
(write-line "item.dwlock = true" writeToVBCode)
(write-line "item.update()" writeToVBCode)
(write-line "item.insulation.status = insulStatus" writeToVBCode)
(write-line "item.update()" writeToVBCode)
(write-line "i = i + 1" writeToVBCode)
(write-line "end while" writeToVBCode)
(write-line "elseif insulationType = \"Liner\" or insulationType = \"liner\" or insulationType = \"LINER\" or insulationType = \"Wrap\" or insulationType = \"wrap\" or insulationType = \"WRAP\" or insulationType = \"Fire\" or insulationType = \"fire\" or insulationType = \"FIRE\" then" writeToVBCode)
(write-line "dim insulationThickness = inputbox(\"Enter insulation thickness:\")" writeToVBCode)
(write-line "while i <= task.selection.count" writeToVBCode)
(write-line "dim item = task.selection[i]" writeToVBCode)
(write-line "if insulationType = \"Liner\" or insulationType = \"liner\" or insulationType = \"LINER\" then" writeToVBCode)
(write-line "dim insulMat = \"HVAC Liner: 1-1/2 LB\"" writeToVBCode)
(write-line "dim insulStatus = \"INSIDE\"" writeToVBCode)
(write-line "item.dwlock = false" writeToVBCode)
(write-line "item.doublewall = false" writeToVBCode)
(write-line "item.dwlock = true" writeToVBCode)
(write-line "item.update()" writeToVBCode)
(write-line "item.insulation.materiallock = false" writeToVBCode)
(write-line "item.insulation.material = insulMat" writeToVBCode)
(write-line "item.insulation.materiallock = true" writeToVBCode)
(write-line "item.insulation.gauge = insulationThickness" writeToVBCode)
(write-line "item.insulation.status = insulStatus" writeToVBCode)
(write-line "item.update()" writeToVBCode)
(write-line "elseif insulationType = \"Wrap\" or insulationType = \"wrap\" or insulationType = \"WRAP\" then" writeToVBCode)
(write-line "dim insulMat = \"HVAC Liner: Duct Wrap\"" writeToVBCode)
(write-line "dim insulStatus = \"OUTSIDE\"" writeToVBCode)
(write-line "item.dwlock = false" writeToVBCode)
(write-line "item.doublewall = false" writeToVBCode)
(write-line "item.dwlock = true" writeToVBCode)
(write-line "item.update()" writeToVBCode)
(write-line "item.insulation.materiallock = false" writeToVBCode)
(write-line "item.insulation.material = insulMat" writeToVBCode)
(write-line "item.insulation.materiallock = true" writeToVBCode)
(write-line "item.insulation.gauge = insulationThickness" writeToVBCode)
(write-line "item.insulation.status = insulStatus" writeToVBCode)
(write-line "item.update()" writeToVBCode)
(write-line "elseif insulationType = \"Fire\" or insulationType = \"fire\" or insulationType = \"FIRE\" then" writeToVBCode)
(write-line "dim insulMat = \"Fire Barrier Duct Wrap: Fire Barrier Duct Wrap\"" writeToVBCode)
(write-line "dim insulStatus = \"OUTSIDE\"" writeToVBCode)
(write-line "item.dwlock = false" writeToVBCode)
(write-line "item.doublewall = false" writeToVBCode)
(write-line "item.dwlock = true" writeToVBCode)
(write-line "item.update()" writeToVBCode)
(write-line "item.insulation.materiallock = false" writeToVBCode)
(write-line "item.insulation.material = insulMat" writeToVBCode)
(write-line "item.insulation.materiallock = true" writeToVBCode)
(write-line "item.insulation.gauge = insulationThickness" writeToVBCode)
(write-line "item.insulation.status = insulStatus" writeToVBCode)
(write-line "item.update()" writeToVBCode)
(write-line "end if" writeToVBCode)
(write-line "i = i + 1" writeToVBCode)
(write-line "end while" writeToVBCode)
(write-line "end if" writeToVBCode)
(write-line "end if" writeToVBCode)
  (close writeToVBCode)
  (Executescript vbCode)
  (vl-file-delete vbCode)
  (princ)
(END_ROUTINE));end defun
;**************************************************************************************************************************************************
(defun c:Dimside_Off () 
;;;; DSF = DIMSIDE OFF - READ DIMS OUTSIDE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "item.dimside = \"outside\"" writeToVBCode)
(write-line "i = i + 1" writeToVBCode)
(write-line "end while" writeToVBCode)
  (close writeToVBCode)
  (Executescript vbCode)
  (vl-file-delete vbCode)
  (princ)
(END_ROUTINE));end defun
;**************************************************************************************************************************************************
(defun c:Dimside_On () 
;;;; DSO = DIMSIDE OFF - READ DIMS INSIDE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "item.dimside = \"inside\"" writeToVBCode)
(write-line "i = i + 1" writeToVBCode)
(write-line "end while" writeToVBCode)
  (close writeToVBCode)
  (Executescript vbCode)
  (vl-file-delete vbCode)
  (princ)
(END_ROUTINE));end defun
;**************************************************************************************************************************************************
(defun c:MultiText_Box ()
  (initcommandversion 1)
  (setq oldCurrent (getvar 'clayer))
  (command "LAYER" "SET" "M-AMC-TEXT" "")
  (initcommandversion 2)
  (setq a (getpoint "\nPick first point: ")
	bX (+ (nth 0 a) 18)
	bY (+ (nth 1 a) 6)
	bZ (nth 2 a)
        b (list bX bY bZ))
  (command "-mtext" a b "" "" "")
  (initcommandversion 1)
  (command "pselect" (entlast) "")
  (command "mtedit")
  (command "LAYER" "SET" oldCurrent "")
  (princ)
(END_ROUTINE));end defun
;**************************************************************************************************************************************************
(defun c:Dimension_at_Elevation ()
  (setvar "cmdecho" 0)
  (command)(command)
  (OUTSIDE_LOOP_VARIABLES nil)
  ;(if(= topSection nil)
  ;  (GET_TOP_SECTION)
  ;);end if
  ;(setq zAdjustment (rtos(+ topSection 1200)2 0)
  ;      zAdjustedUCS (list (list(car(getvar "UCSORG"))(cadr(getvar "UCSORG")) (atoi zAdjustment))(trans (list 1 0 0)1 0)(trans(list 0 1 0)1 0)))
  ;((if command-s command-s vl-cmdf) "_.UCS" "_origin" "_none" (trans(car zAdjustedUCS)0 1) "_none" (trans(cadr zAdjustedUCS)0 1) "_none" (trans(caddr zAdjustedUCS)0 1))
  (setq curOSnap (getvar 'osnapz))
  (setvar 'osnapz 0)
  (setq pt1 nil
        pt2 nil
        dimElev nil
        dimPt1 nil
        dimPt2 nil
        pt1 (getpoint "\nPick first point: "))(terpri)
  (setq orginalOSMode (getvar 'osmode))
  (setq pt2 (getpoint pt1 "\nPick second point: "))(terpri)
  (if(>(caddr pt1)(caddr pt2))
    (setq dimElev (ROUNDUP(caddr pt1)12000))
    (setq dimElev (ROUNDUP(caddr pt2)12000))
  );end if
  (if(= dimElev nil)
    (setq dimElev 12000)
  );end if
  (setq dimPt1 (list (car pt1)(cadr pt1)0)
        dimPt2 (list (car pt2)(cadr pt2)0))
  (initcommandversion 1)
  (setq oldCurrentLayer (getvar 'clayer))
  (command "LAYER" "SET" "M-AMC-GDIM-USER" "")
  (initcommandversion 2)
  (setvar 'osmode (logior (getvar 'osmode) 16384))
  (command "._dimlinear" dimPt1 dimPt2 pause)
  (initcommandversion 1)
  (setvar 'osmode (logior (getvar 'osmode) 16384))
  (command "move" (entlast) "" '(0.0 0.0 0.0) (strcat "@0,0," (rtos dimElev)))
  (setvar 'osmode orginalOSMode)
  (command "LAYER" "SET" oldCurrentLayer "")
  (setvar 'osnapz curOSnap)
  ;(if(not(or(wcmatch UCSname "WCS")(wcmatch UCSname "Unnamed")))
  ;  (command "_.UCS" "Named" "Restore" UCSname "")
  ;  (resetUCS)
  ;);end if
  (princ)
  (END_ROUTINE)
  (command "pselect" (entlast) "")
  );end defun
;**************************************************************************************************************************************************
(defun c:Create_DoubleWall_Patterns (/ doublewsset i limit mysnap ent innerPatterns)
  (setq doublewsset (ssget  '((0 . "MAPS_SOLID")));Choose selection set
        i 0
	a "false"
        dwlimit (sslength doublewsset));Set loop limit
    (while (< i dwlimit);Start the Loop
      (setq dwent (ssname doublewsset i)
            dwentlist (entget(ssname doublewsset i))
            dwItemCID (cdr(nth 9 dwentlist)));end setq
      (if (and(= a "false")(or ;set mini loop / condition designator
        (wcmatch dwItemCID "40")
        (wcmatch dwItemCID "866")
        (wcmatch dwItemCID "330")
        (wcmatch dwItemCID "8")
        (wcmatch dwItemCID "30")
        (wcmatch dwItemCID "2")
        (wcmatch dwItemCID "522")
        (wcmatch dwItemCID "802")
        (wcmatch dwItemCID "382")
        (wcmatch dwItemCID "1")
        (wcmatch dwItemCID "505")
        (wcmatch dwItemCID "519")
        (wcmatch dwItemCID "20")
        (wcmatch dwItemCID "17")))
          (progn(setq roofDuct (ssadd); Create ss of patterns
                      firstOuter dwent);end setq
                (ssadd firstOuter roofDuct)
                (setq a "true")
                (setq i (1+ i)));end progn (then) / Add first pattern to ss
          (if (and(= a "true")(or
            (wcmatch dwItemCID "40")
            (wcmatch dwItemCID "866")
            (wcmatch dwItemCID "330")
            (wcmatch dwItemCID "8")
            (wcmatch dwItemCID "30")
            (wcmatch dwItemCID "2")
            (wcmatch dwItemCID "522")
            (wcmatch dwItemCID "802")
            (wcmatch dwItemCID "382")
            (wcmatch dwItemCID "1")
            (wcmatch dwItemCID "505")
            (wcmatch dwItemCID "519")
            (wcmatch dwItemCID "20")
            (wcmatch dwItemCID "17")))
              (progn(setq addOuter dwent)
              (ssadd addOuter roofDuct);end progn (else) / Add subsequent patterns per loop
              (setq i (1+ i)));increment the parent loop
              (if (not(or
                (wcmatch dwItemCID "40")
                (wcmatch dwItemCID "866")
                (wcmatch dwItemCID "330")
                (wcmatch dwItemCID "8")
                (wcmatch dwItemCID "30")
                (wcmatch dwItemCID "2")
                (wcmatch dwItemCID "522")
                (wcmatch dwItemCID "802")
                (wcmatch dwItemCID "382")
                (wcmatch dwItemCID "1")
                (wcmatch dwItemCID "505")
                (wcmatch dwItemCID "519")
                (wcmatch dwItemCID "20")
                (wcmatch dwItemCID "17")))
                  (setq i (1+ i));increment the parent loop
              );end if
	  );end if
      );end if
   );end while
   (if(not(=(sslength roofDuct) nil));If sset isn't empty...
    (progn
      (setq j 0;set the count
            limit (sslength roofDuct);Set loop limit
            mysnap (getvar "osmode");Save snap settings
            );end setq
      (setvar "osmode" 0)
      (command "ucs" "world")
      (while (< j limit);Start the Loop
        (setq ent (ssname roofDuct j)
              entlist (entget(ssname roofDuct j))
              ItemCID (cdr(nth 9 entlist)));end setq
        (command "_.copybase" '(0 0 0) ent "")
        (command "_.pasteclip" '(0 0 0))
        (if (< j 1)
            (progn(setq innerPatterns (ssadd); Create ss of patterns
                        firstPattern (entlast));end setq
            (ssadd firstPattern innerPatterns));end progn (then) / Add first pattern to ss
              (progn(setq addPattern (entlast))
              (ssadd addPattern innerPatterns));end progn (else) / Add subsequent patterns per loop
        );end if
            (setq j (1+ j));increment loop by 1
      );end while
      (setvar "osmode" mysnap)
      (command "pselect" innerPatterns "")
(OUTSIDE_LOOP_VARIABLES nil)
(write-line "dim insGauge = item.insulation.gauge" writeToVBCode)
(write-line "item.alias = \"InsidePattern\"" writeToVBCode)
(write-line "item.insulation.status = \"OFF\"" writeToVBCode)
(write-line "rem Reduce Size and Adjust Length for Inside Pattern" writeToVBCode)
(write-line "if item.CID = 40 or item.CID = 522 then" writeToVBCode)
(write-line "dim length = item.dim[\"Length\"].numvalue - 0.25" writeToVBCode)
(write-line "item.dim[1].value = item.dim[1].value - (insGauge * 2)" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[\"Length\"].value = length" writeToVBCode)
(write-line "item.notes = \"Doublewall Inside Pattern\"" writeToVBCode)
(write-line "item.update()" writeToVBCode)
(write-line "elseif item.CID = 866 or item.CID = 802 or item.CID = 30 or item.CID = 382 or item.CID = 1 or item.CID = 505 or item.CID = 519 then" writeToVBCode)
(write-line "dim length = item.dim[\"Length\"].numvalue - 0.25" writeToVBCode)
(write-line "item.dim[1].value = item.dim[1].value - (insGauge * 2)" writeToVBCode)
(write-line "item.dim[2].value = item.dim[2].value - (insGauge * 2)" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[\"Length\"].value = length" writeToVBCode)
(write-line "item.notes = \"Doublewall Inside Pattern\"" writeToVBCode)
(write-line "item.update()" writeToVBCode)
(write-line "elseif item.CID = 20 then" writeToVBCode)
(write-line "item.dim[1].value = item.dim[1].value - (insGauge * 2)" writeToVBCode)
(write-line "item.dim[2].value = item.dim[2].value - (insGauge * 2)" writeToVBCode)
(write-line "if (wildcard(item.dim[3].value,\"Equal\") = 1) then" writeToVBCode)
(write-line "item.dim[3].value = item.dim[1].value" writeToVBCode)
(write-line "elseif (wildcard(item.dim[3].value,\"Equal\") = 0) then" writeToVBCode)
(write-line "item.dim[3].value = item.dim[3].value - (insGauge * 2)" writeToVBCode)
(write-line "item.update()" writeToVBCode)
(write-line "end if" writeToVBCode)
(write-line "dim ItemCID20Length1 = item.dim[5].value + (insGauge - 0.125)" writeToVBCode)
(write-line "dim ItemCID20Length2 = item.dim[6].value + (insGauge - 0.125)" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[5].value = ItemCID20Length1" writeToVBCode)
(write-line "item.dim[6].value = ItemCID20Length2" writeToVBCode)
(write-line "item.notes = \"Doublewall Inside Pattern\"" writeToVBCode)
(write-line "item.update()" writeToVBCode)
(write-line "elseif item.CID = 17 then" writeToVBCode)
(write-line "item.dim[1].value = item.dim[1].value - (insGauge * 2)" writeToVBCode)
(write-line "item.dim[2].value = item.dim[2].value - (insGauge * 2)" writeToVBCode)
(write-line "if (wildcard(item.dim[3].value,\"Equal\") = 1) then" writeToVBCode)
(write-line "item.dim[3].value = item.dim[1].value" writeToVBCode)
(write-line "elseif (wildcard(item.dim[3].value,\"Equal\") = 0) then" writeToVBCode)
(write-line "item.dim[3].value = item.dim[3].value - (insGauge * 2)" writeToVBCode)
(write-line "item.update()" writeToVBCode)
(write-line "end if" writeToVBCode)
(write-line "if (wildcard(item.dim[7].value, \"Width\") = 1) then" writeToVBCode)
(write-line "dim length = item.dim[1].numvalue + ((insGauge * 2) - 0.25)" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[7].value = length" writeToVBCode)
(write-line "elseif (wildcard(item.dim[7].value, \"Half Width\") = 1) then" writeToVBCode)
(write-line "dim length = (item.dim[1].numvalue / 2) + ((insGauge * 2) - 0.25)" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[7].value = length" writeToVBCode)
(write-line "else" writeToVBCode)
(write-line "dim length = item.dim[7].numvalue + ((insGauge * 2) - 0.25)" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[7].value = length" writeToVBCode)
(write-line "end if" writeToVBCode)
(write-line "item.notes = \"Doublewall Inside Pattern\"" writeToVBCode)
(write-line "item.update()" writeToVBCode)
(write-line "elseif item.CID = 8 then" writeToVBCode)
(write-line "dim length = item.dim[\"Length\"].numvalue - 0.25" writeToVBCode)
(write-line "item.dim[1].value = item.dim[1].value - (insGauge * 2)" writeToVBCode)
(write-line "item.dim[2].value = item.dim[2].value - (insGauge * 2)" writeToVBCode)
(write-line "if (wildcard(item.dim[3].value,\"Equal\") = 1) then" writeToVBCode)
(write-line "item.dim[3].value = item.dim[1].value" writeToVBCode)
(write-line "elseif (wildcard(item.dim[3].value,\"Equal\") = 0) then" writeToVBCode)
(write-line "item.dim[3].value = item.dim[3].value - (insGauge * 2)" writeToVBCode)
(write-line "item.update()" writeToVBCode)
(write-line "end if" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[\"Length\"].value = length" writeToVBCode)
(write-line "item.notes = \"Doublewall Inside Pattern\"" writeToVBCode)
(write-line "item.update()" writeToVBCode)
(write-line "elseif item.CID = 330 or item.CID = 2 then" writeToVBCode)
(write-line "dim length = item.dim[\"Length\"].numvalue - 0.25" writeToVBCode)
(write-line "item.dim[1].value = item.dim[1].value - (insGauge * 2)" writeToVBCode)
(write-line "item.dim[2].value = item.dim[2].value - (insGauge * 2)" writeToVBCode)
(write-line "item.dim[3].value = item.dim[3].value - (insGauge * 2)" writeToVBCode)
(write-line "if (wildcard(item.dim[3].value,\"Equal\") = 1) then" writeToVBCode)
(write-line "item.dim[4].value = item.dim[2].value" writeToVBCode)
(write-line "item.update()" writeToVBCode)
(write-line "elseif (wildcard(item.dim[3].value,\"Equal\") = 0) then" writeToVBCode)
(write-line "item.dim[4].value = item.dim[4].value - (insGauge * 2)" writeToVBCode)
(write-line "item.update()" writeToVBCode)
(write-line "end if" writeToVBCode)
(write-line "item.connector[1].value = \"None\"" writeToVBCode)
(write-line "item.connector[1].locked = true" writeToVBCode)
(write-line "item.connector[2].value = \"None\"" writeToVBCode)
(write-line "item.connector[2].locked = true" writeToVBCode)
(write-line "item.dim[\"Length\"].value = length" writeToVBCode)
(write-line "item.notes = \"Doublewall Inside Pattern\"" writeToVBCode)
(write-line "item.update()" writeToVBCode)
(write-line "end if" writeToVBCode)
(write-line "item.update()" writeToVBCode)
      (close writeToVBCode)
      (Executescript vbCode)
      (vl-file-delete vbCode)
      (removemaptext innerPatterns 127)
      (settext innerPatterns 8 "on")
      (command "pselect" innerPatterns "")
      (princ)
    );end progn
  );end if
(END_ROUTINE));end defun
;**************************************************************************************************************************************************
(defun c:Select_DoubleWall_Patterns (/)
  (vl-load-com)
  (setq aliasDW (ssget "_X" '((0 . "MAPS_SOLID")));Choose selection set
        i 0
        limit (sslength aliasDW);Set loop limit
        DWpats (ssadd))
    (while (< i limit);Start the Loop
      (setq ent (ssname aliasDW i)
            entlist (entget(ssname aliasDW i))
            ItemCID (cdr(nth 9 entlist))
            Notes (vlax-get-property (vlax-ename->vla-object ent) "Notes"));end setq
      (if(wcmatch Notes "Doublewall Inside Pattern")
        (ssadd ent DWpats)
      );end if
          (setq i (1+ i));increment the parent loop
    );endwhile
  (command "pselect" DWpats "")
(END_ROUTINE));end defun
;**************************************************************************************************************************************************
(defun c:S0 ();Snaps 0 - No Snaps
  (setvar 'osmode 16384)
  (setq snapNumb (getvar 'osmode))
  (prompt "Unchecked all snaps; Current OSMode # is: ")(princ snapNumb)
  (princ)
(END_ROUTINE));end defun
;**************************************************************************************************************************************************
(defun c:S1 ();Snaps 1 - Center & Node
  (setvar 'osmode 12)
  (setq snapNumb (getvar 'osmode))
  (prompt "CENTER & NODE snaps active; Current OSMode # is: ")(princ snapNumb)
  (princ)
(END_ROUTINE));end defun
;**************************************************************************************************************************************************
(defun c:S2 ();Snaps 2 - Endpoint & Perpendicular
  (setvar 'osmode 129)
  (setq snapNumb (getvar 'osmode))
  (prompt "ENDPOINT & PERPENDICULAR snaps active; Current OSMode # is: ")(princ snapNumb)
  (princ)
(END_ROUTINE));end defun
;**************************************************************************************************************************************************
(defun c:S3 ();Snaps 3 - Center & Perpendicular
  (setvar 'osmode 132)
  (setq snapNumb (getvar 'osmode))
  (prompt "CENTER & PERPENDICULAR snaps active; Current OSMode # is: ")(princ snapNumb)
  (princ)
(END_ROUTINE));end defun
;**************************************************************************************************************************************************
(defun c:S4 ();Snaps 4 - Center & Quadrant
  (setvar 'osmode 20)
  (setq snapNumb (getvar 'osmode))
  (prompt "CENTER & QUARDRANT snaps active; Current OSMode # is: ")(princ snapNumb)
  (princ)
(END_ROUTINE));end defun
;**************************************************************************************************************************************************
(defun c:S5 ();Snaps 5 - Just Endpoint
  (setvar 'osmode 1)
  (setq snapNumb (getvar 'osmode))
  (prompt "Only ENDPOINT snaps active; Current OSMode # is: ")(princ snapNumb)
  (princ)
(END_ROUTINE));end defun
;**************************************************************************************************************************************************
(defun c:S6 ();Snaps 6 - Just Perpendicular
  (setvar 'osmode 128)
  (setq snapNumb (getvar 'osmode))
  (prompt "Only PERPENDICULAR snaps active; Current OSMode # is: ")(princ snapNumb)
  (princ)
(END_ROUTINE));end defun
;**************************************************************************************************************************************************
(defun c:S7 ();Snaps 7 - Just Midpoint
  (setvar 'osmode 2)
  (setq snapNumb (getvar 'osmode))
  (prompt "Only MIDPOINT snaps active; Current OSMode # is: ")(princ snapNumb)
  (princ)
(END_ROUTINE));end defun
;**************************************************************************************************************************************************
(defun c:S8 ();Snaps 8 - Just Intersection
  (setvar 'osmode 32)
  (setq snapNumb (getvar 'osmode))
  (prompt "Only INTERSECTION snaps active; Current OSMode # is: ")(princ snapNumb)
  (princ)
(END_ROUTINE));end defun
;**************************************************************************************************************************************************
(defun c:S9 ();Snaps 3 - Center & Perpendicular
  (setvar 'osmode 140)
  (setq snapNumb (getvar 'osmode))
  (prompt "CENTER, NODE & PERPENDICULAR snaps active; Current OSMode # is: ")(princ snapNumb)
  (princ)
(END_ROUTINE));end defun
;**************************************************************************************************************************************************
(defun c:Rotate_Reference () 
  ;;;; RR = ROTATE REFERENCE
  (setq i 0
        sset (ssget))
  (OUTSIDE_LOOP_VARIABLES sset)
  (command "UCS" "W")
  (INSIDE_LOOP_VARIABLES sset i)
  (setq pt1 (getpoint "\nPick base point: "));end setq
  (setq pt2 (getpoint pt1 "\nPick reference point: "))
  (command "UCS" "VIEW")
  (command "CAL" "translatedPt1=w2u(pt1)")
  (command "CAL" "translatedPt2=w2u(pt2)")
  (command "_ROTATE" sset "" translatedPt1 "R" translatedPt1 translatedPt2 PAUSE)
  (command "CAL" "ucsC1xyz=w2u(c1xyz)")
  (command "UCS" "M" (strcat(rtos(car ucsC1xyz)2) "," (rtos(cadr ucsC1xyz)2) "," (rtos(caddr ucsC1xyz)2)))
(princ)
(END_ROUTINE));end defun
;**************************************************************************************************************************************************
(defun c:Item_Specification_Repair ()
;;;; ISR = SPECIFICATION REPAIR
  (OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if (wildcard(item.service,\"*combustion*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*-10*\") = 1) then" writeToVBCode)
(write-line "item.speclock = false" writeToVBCode)
(write-line "item.gaugelock = false" writeToVBCode)
(write-line "item.specification = \"-10''\"" writeToVBCode)
(write-line "item.speclock = true" writeToVBCode)
(write-line "item.update()" writeToVBCode)
(write-line "elseif (wildcard(item.service,\"*exhaust*\" + \"*-6*\") = 1) then" writeToVBCode)
(write-line "item.speclock = false" writeToVBCode)
(write-line "item.gaugelock = false" writeToVBCode)
(write-line "item.specification = \"-6''\"" writeToVBCode)
(write-line "item.speclock = true" writeToVBCode)
(write-line "item.update()" writeToVBCode)
(write-line "elseif (wildcard(item.service,\"*exhaust*\" + \"*-4*\") = 1) then" writeToVBCode)
(write-line "item.speclock = false" writeToVBCode)
(write-line "item.gaugelock = false" writeToVBCode)
(write-line "item.specification = \"-4''\"" writeToVBCode)
(write-line "item.speclock = true" writeToVBCode)
(write-line "item.update()" writeToVBCode)
(write-line "elseif (wildcard(item.service,\"*exhaust*\" + \"*inslab*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*low*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*medium*\") = 1) then" writeToVBCode)
(write-line "item.speclock = false" writeToVBCode)
(write-line "item.gaugelock = false" writeToVBCode)
(write-line "item.specification = \"-3''\"" writeToVBCode)
(write-line "item.speclock = true" writeToVBCode)
(write-line "item.update()" writeToVBCode)
(write-line "elseif (wildcard(item.service,\"*exhaust*\" + \"*weld*\" + \"*-10*\") = 1) then" writeToVBCode)
(write-line "item.speclock = false" writeToVBCode)
(write-line "item.gaugelock = false" writeToVBCode)
(write-line "item.specification = \"-10''\"" writeToVBCode)
(write-line "item.speclock = true" writeToVBCode)
(write-line "item.update()" writeToVBCode)
(write-line "elseif (wildcard(item.service,\"*exhaust*\" + \"*weld*\" + \"*-6*\") = 1) then" writeToVBCode)
(write-line "item.speclock = false" writeToVBCode)
(write-line "item.gaugelock = false" writeToVBCode)
(write-line "item.specification = \"-6''\"" writeToVBCode)
(write-line "item.speclock = true" writeToVBCode)
(write-line "item.update()" writeToVBCode)
(write-line "elseif (wildcard(item.service,\"*exhaust*\" + \"*weld*\" + \"*-4*\") = 1) then" writeToVBCode)
(write-line "item.speclock = false" writeToVBCode)
(write-line "item.gaugelock = false" writeToVBCode)
(write-line "item.specification = \"-4''\"" writeToVBCode)
(write-line "item.speclock = true" writeToVBCode)
(write-line "item.update()" writeToVBCode)
(write-line "elseif (wildcard(item.service,\"*exhaust*\" + \"*weld*\" + \"*-2*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*outside*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*return*\" + \"*-10*\") = 1) then" writeToVBCode)
(write-line "item.speclock = false" writeToVBCode)
(write-line "item.gaugelock = false" writeToVBCode)
(write-line "item.specification = \"-10''\"" writeToVBCode)
(write-line "item.speclock = true" writeToVBCode)
(write-line "item.update()" writeToVBCode)
(write-line "elseif (wildcard(item.service,\"*return*\" + \"*-6*\") = 1) then" writeToVBCode)
(write-line "item.speclock = false" writeToVBCode)
(write-line "item.gaugelock = false" writeToVBCode)
(write-line "item.specification = \"-6''\"" writeToVBCode)
(write-line "item.speclock = true" writeToVBCode)
(write-line "item.update()" writeToVBCode)
(write-line "elseif (wildcard(item.service,\"*return*\" + \"*-4*\") = 1) then" writeToVBCode)
(write-line "item.speclock = false" writeToVBCode)
(write-line "item.gaugelock = false" writeToVBCode)
(write-line "item.specification = \"-4''\"" writeToVBCode)
(write-line "item.speclock = true" writeToVBCode)
(write-line "item.update()" writeToVBCode)
(write-line "elseif (wildcard(item.service,\"*return*\" + \"*-2*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*return*\" + \"*medium*\") = 1) then" writeToVBCode)
(write-line "item.speclock = false" writeToVBCode)
(write-line "item.gaugelock = false" writeToVBCode)
(write-line "item.specification = \"-3''\"" writeToVBCode)
(write-line "item.speclock = true" writeToVBCode)
(write-line "item.update()" writeToVBCode)
(write-line "elseif (wildcard(item.service,\"*supply*\" + \"*+10*\") = 1) then" writeToVBCode)
(write-line "item.speclock = false" writeToVBCode)
(write-line "item.gaugelock = false" writeToVBCode)
(write-line "item.specification = \"+10''\"" writeToVBCode)
(write-line "item.speclock = true" writeToVBCode)
(write-line "item.update()" writeToVBCode)
(write-line "elseif (wildcard(item.service,\"*supply*\" + \"*+6*\") = 1) then" writeToVBCode)
(write-line "item.speclock = false" writeToVBCode)
(write-line "item.gaugelock = false" writeToVBCode)
(write-line "item.specification = \"+6''\"" writeToVBCode)
(write-line "item.speclock = true" writeToVBCode)
(write-line "item.update()" writeToVBCode)
(write-line "elseif (wildcard(item.service,\"*supply*\" + \"*+4*\") = 1) then" writeToVBCode)
(write-line "item.speclock = false" writeToVBCode)
(write-line "item.gaugelock = false" writeToVBCode)
(write-line "item.specification = \"+4''\"" writeToVBCode)
(write-line "item.speclock = true" writeToVBCode)
(write-line "item.update()" writeToVBCode)
(write-line "elseif (wildcard(item.service,\"*supply*\" + \"*medium*\") = 1) then" writeToVBCode)
(write-line "item.speclock = false" writeToVBCode)
(write-line "item.gaugelock = false" writeToVBCode)
(write-line "item.specification = \"+3''\"" writeToVBCode)
(write-line "item.speclock = true" writeToVBCode)
(write-line "item.update()" writeToVBCode)
(write-line "elseif (wildcard(item.service,\"*supply*\" + \"*low*\") = 1) then" writeToVBCode)
(write-line "item.speclock = false" writeToVBCode)
(write-line "item.gaugelock = false" writeToVBCode)
(write-line "item.specification = \"+2''\"" writeToVBCode)
(write-line "item.speclock = true" writeToVBCode)
(write-line "item.update()" writeToVBCode)
(write-line "elseif (wildcard(item.service,\"*transfer*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "end if" writeToVBCode)
(write-line "i = i + 1" writeToVBCode)
(write-line "end while" writeToVBCode)
  (close writeToVBCode)
  (Executescript vbCode)
  (vl-file-delete vbCode)
  (prompt "Item specification re-evaluated.")(princ)
  (princ)
(END_ROUTINE));end defun
;**************************************************************************************************************************************************
(defun c:Insert_ACAD_Layout_Points (/)
  ; Apply Trimble Points
  (vl-load-com)
  (setq sset (ssget "_X" '((0 . "MAPS_SOLID")));Choose selection set
        i 0);end setq
  (OUTSIDE_LOOP_VARIABLES sset)
  (if(not(= sset nil))
    (progn
    (command "_.-insert" seismicBlock (list 0 0 0) "" "" "")
    (command "explode" (entlast))
    (setq refPoint (entlast));end setq
    (command "-purge" "B" "TrimbleSeismic" "N" "")
    (while (< i limit);Start the Loop
      (INSIDE_LOOP_VARIABLES sset i)
      (if(wcmatch ItemNotes "Seismic Flag: Leave Untouched")
        (command "._erase" ent ""));end if
      (if(wcmatch ItemSourceFileName "Seismic Rectangular")
        (progn
          (setq coordinates (list c4x c4y (- c4z 4)));end setq
          (command "copy" refPoint "" "@" coordinates)
          (vlax-put-property(vlax-ename->vla-object (entlast)) 'Notes "Seismic Flag: Leave Untouched")
        );end progn
        (if(wcmatch ItemSourceFileName "Seismic")
          (progn
            (setq coordinates (list c13x c13y c13z));end setq
            (command "copy" refPoint "" "@" coordinates)
            (vlax-put-property(vlax-ename->vla-object (entlast)) 'Notes "Seismic Flag: Leave Untouched")
          );end progn
        );end if
      );end if
          (setq i (1+ i));increment the parent loop
    );endwhile
    );end progn
  );end if
  (close writeToVBCode)
  (vl-file-delete vbCode)
  (princ)
(END_ROUTINE));end defun
;**************************************************************************************************************************************************
(defun c:Item_Information_Dump (/ item);DEVELOPMENT TOOL
  (vl-load-com)
  (setq sset (ssget)
        i 0)
  (OUTSIDE_LOOP_VARIABLES nil)
  (INSIDE_LOOP_VARIABLES sset i)
  (princ "********************************************************************************")(princ)(terpri)
  (princ "**************************VisualLisp ''VLAX'' Exposure**************************")(princ)(terpri)
  (princ "********************************************************************************")(princ)(terpri)
    (vlax-dump-object vla);end vlax dump
    (princ " ")(terpri)
    (princ)
  (princ "********************************************************************************")(princ)(terpri)
  (princ "*****************************List Command Exposure******************************")(princ)(terpri)
  (princ "********************************************************************************")(princ)(terpri)
    (command "list" ent "" "" "" "" "");end list command
    (princ)
  (princ "********************************************************************************")(princ)(terpri)
  (princ "***********************VisualLisp Map Property Exposure*************************")(princ)(terpri)
  (princ "********************************************************************************")(princ)(terpri)
  (if(wcmatch entGraphicID "MAPS_SOLID")
    (progn
      (foreach item '("Area" "CustomData" "Description"
                      "Elevation" "EndSize" "ItemNumber"
                      "LengthAngle" "Notes" "Points"
                      "Section" "ServiceName" "Status"
                      "Weight");end item list
      (princ (strcat "\n " item " = "))
      (princ (vlax-get-property vla item))
      );end foreach
    (princ)(terpri)
    );end progn
  );end if
  (princ "********************************************************************************")(princ)(terpri)
  (princ "************************AutoLisp ''List Setup'' Exposure************************")(princ)(terpri)
  (princ "********************************************************************************")(princ)(terpri)
  (princ entlist)(terpri);end entity list print
  (setq entlistCount 0)
  (foreach el entlist (terpri)(princ(strcat "List index " (itoa entlistCount) " = "))(princ el)(setq entlistCount (1+ entlistCount)))
  (terpri)
  (textscr)
  (princ)
(END_ROUTINE));end defun
;**************************************************************************************************************************************************
(defun c:Layout_Prep ()
  (setvar "cmdecho" 0)
  (print "Do you want your 2D drawing scaled down?")(princ)(terpri)
  (print "1: Yes - Drawing will be scaled.")(princ)(terpri)
  (print "2: No - Drawing will not be scaled.")(princ)(terpri)
  (initget 0 "Yes No")
  (setq scaleTest (getkword "\nChoose: [Yes/No] <No>?:"))
  (if (= scaleTest nil)
    (setq scaleTest "No")
  );end if
  (terpri)
  (print "Do you want explode blocks to find nested layout points?")(princ)(terpri)
  (print "1: Yes - Blocked points will be evaluated.")(princ)(terpri)
  (print "2: No - Blocked points are ignored.")(princ)(terpri)
  (initget 0 "Yes No")
  (setq nestedPointTest (getkword "\nChoose: [Yes/No] <No>?:"))
  (if (= nestedPointTest nil)
    (setq nestedPointTest "No")
  );end if
  (c:Improved_ReNumber)
  (c:Improved_Point_Export)
  (c:Create_2D)
  (startapp excel (strcat "\"" pointFileCSVLoc "\""))
(END_ROUTINE));end defun
;**************************************************************************************************************************************************
(defun c:Improved_ReNumber (/)
  ; IMPROVED RENUMBER
  (vl-load-com)
  (c:World_View)
  (setvar "cmdecho" 0)
  (setq sset (ssget "X"
             '(
              (-4 . "<AND")
                (0 . "MAPS_SOLID")
                (-4 . "<NOT")
                  (0 . "INSERT")
                (-4 . "NOT>")
              (-4 . "AND>")
              );close quote func
             );end ssget
        i 0
        c 1
        e 1
        o 1
        r 1
        s 1
        tr 1
        misc 1
        h 1
        bo 1
        ep 1
        fs 1
        tp 1
        misc3d (ssadd)
        non3d (ssget "X" '((-4 . "<NOT")(0 . "MAPS_SOLID")(-4 . "NOT>"))));end setq
  (OUTSIDE_LOOP_VARIABLES sset)
  (write-line "item.number = item.customdata[1].value" writeToVBCode)
  (close writeToVBCode)
    (while (< i limit);Start the Loop
      (INSIDE_LOOP_VARIABLES sset i)
      (if(and(wcmatch (strcase ItemService) "*COMBUSTION*")
         (not(or allSupport
                 trimblePoint
                 blockout
                 roundBlockout
                 (wcmatch(strcase ItemSourceFileName)(strcase "EQUIPMENT PAD"))
                 (wcmatch(strcase ItemSourceFileName)(strcase "FLOOR BLOCK OUT"))
                 (wcmatch(strcase ItemSourceFileName)(strcase "WALL BLOCK OUT")))))
        (setq prefix "C"
	      itm# (rtos c 2 0)
              c (1+ c))
        (if(and(wcmatch (strcase ItemService) "*EXHAUST*")
           (not(or allSupport
                   trimblePoint
                   blockout
                   roundBlockout
                   (wcmatch(strcase ItemSourceFileName)(strcase "EQUIPMENT PAD"))
                   (wcmatch(strcase ItemSourceFileName)(strcase "FLOOR BLOCK OUT"))
                   (wcmatch(strcase ItemSourceFileName)(strcase "WALL BLOCK OUT")))))
          (setq prefix "E"
	        itm# (rtos e 2 0)
                e (1+ e))
          (if(and(wcmatch (strcase ItemService) "*OUTSIDE*")
             (not(or allSupport
                     trimblePoint
                     blockout
                     roundBlockout
                     (wcmatch(strcase ItemSourceFileName)(strcase "EQUIPMENT PAD"))
                     (wcmatch(strcase ItemSourceFileName)(strcase "FLOOR BLOCK OUT"))
                     (wcmatch(strcase ItemSourceFileName)(strcase "WALL BLOCK OUT")))))
            (setq prefix "O"
	          itm# (rtos o 2 0)
                  o (1+ o))
            (if(and(wcmatch (strcase ItemService) "*RETURN*")
               (not(or allSupport
                       trimblePoint
                       blockout
                       roundBlockout
                       (wcmatch(strcase ItemSourceFileName)(strcase "EQUIPMENT PAD"))
                       (wcmatch(strcase ItemSourceFileName)(strcase "FLOOR BLOCK OUT"))
                       (wcmatch(strcase ItemSourceFileName)(strcase "WALL BLOCK OUT")))))
              (setq prefix "R"
	            itm# (rtos r 2 0)
                    r (1+ r))
              (if(and(wcmatch (strcase ItemService) "*SUPPLY*")
                 (not(or allSupport
                         trimblePoint
                         blockout
                         roundBlockout
                         (wcmatch(strcase ItemSourceFileName)(strcase "EQUIPMENT PAD"))
                         (wcmatch(strcase ItemSourceFileName)(strcase "FLOOR BLOCK OUT"))
                         (wcmatch(strcase ItemSourceFileName)(strcase "WALL BLOCK OUT")))))
                (setq prefix "S"
	              itm# (rtos s 2 0)
                      s (1+ s))
                (if(and(wcmatch (strcase ItemService) "*TRANSFER*")
                   (not(or allSupport
                           trimblePoint
                           blockout
                           roundBlockout
                           (wcmatch(strcase ItemSourceFileName)(strcase "EQUIPMENT PAD"))
                           (wcmatch(strcase ItemSourceFileName)(strcase "FLOOR BLOCK OUT"))
                           (wcmatch(strcase ItemSourceFileName)(strcase "WALL BLOCK OUT")))))
                  (setq prefix "T"
	                itm# (rtos tr 2 0)
                        tr (1+ tr))
                    (if hangerSupport&Seismic
                      (setq prefix "H"
	                    itm# (rtos h 2 0)
                            h (1+ h))
                      (if trimblePoint
                        (setq prefix "TP"
	                      itm# (rtos tp 2 0)
                              tp (1+ tp))
                        (if floorSupport
                          (setq prefix "FS"
	                        itm# (rtos fs 2 0)
                                fs (1+ fs))
                          (if(or blockout roundBlockout (wcmatch(strcase ItemSourceFileName)(strcase "FLOOR BLOCK OUT"))(wcmatch(strcase ItemSourceFileName)(strcase "WALL BLOCK OUT")))
                            (setq prefix "BO"
	                          itm# (rtos bo 2 0)
                                  bo (1+ bo))
                            (if(wcmatch(strcase ItemSourceFileName)(strcase "EQUIPMENT PAD"))
                              (setq prefix "EP"
	                            itm# (rtos ep 2 0)
                                    ep (1+ ep))
                  (if(not(or(wcmatch (strcase ItemService) "*COMBUSTION*")
                            (wcmatch (strcase ItemService) "*EXHAUST*")
                            (wcmatch (strcase ItemService) "*OUTSIDE*")
                            (wcmatch (strcase ItemService) "*RETURN*")
                            (wcmatch (strcase ItemService) "*SUPPLY*")
                            (wcmatch (strcase ItemService) "*TRANSFER*")
                            (wcmatch (strcase ItemService) "*TRIMBLE*")))
                    (setq prefix ""
	                  itm# (rtos misc 2 0)
                          misc (1+ misc))
      ) ) ) ) ) ) ) ) ) ) ) );end ifs
      (if(= prefix nil)(setq prefix ""))
      (if(= itm# nil)(setq itm# ""))
      (vlax-put-property vla "CustomData" (strcat itemCustomData1Name " = " prefix itm# ","))
      (executescript vbCode SSentity)
    (setq i (1+ i));increment the main loop
  );endwhile
  (vl-file-delete vbCode)
(END_ROUTINE));end defun
;**************************************************************************************************************************************************
(defun c:Improved_Point_Export (/)
  ; IMPROVED POINT EXPORT
  (if(= nestedPointTest nil)
    (progn
      (print "Do you want explode blocks to find nested layout points?")(princ)(terpri)
      (print "1: Yes - Blocked points will be evaluated.")(princ)(terpri)
      (print "2: No - Blocked points are ignored.")(princ)(terpri)
      (initget 0 "Yes No")
      (setq nestedPointTest (getkword "\nChoose: [Yes/No] <No>?:"))
      (if (= nestedPointTest nil)
        (setq nestedPointTest "No")
      );end if
    );end progn
  );end if
  (vl-load-com)
  (OUTSIDE_LOOP_VARIABLES nil)
  (command "_qsave" "")
  (if(not(= dwgLink nil))
    (progn
      (STRING_SPLIT "/" dwgLink)
      (setq folderString (strcat nth0 "/" nth1 "/07)FABRICATION/03) SHEET METAL/"))
      (if(vl-file-directory-p folderString)
        (progn
          (setq pointFileCSVLoc (strcat folderString dwgName "_Coordinates.csv")
                saveBackup (strcat folderString dwgName "_backup_" (rtos month 2 0) "-" (rtos day 2 0) "-" (rtos year 2 0) "@" (rtos hour 2 0) "hr" (rtos minute 2 0) "m" (rtos second 2 0) "s" (rtos milliSecond 2 0) "ms" ".dwg")
          );end setq
          (command "_.save" saveBackup (if(/=(getvar 'cmdactive)0) "_Y") "")(command)
        );progn
        (progn
          (setq pointFileCSVLoc (strcat dwgDirectory dwgName "_Coordinates.csv")
                saveBackup (strcat dwgDirectory dwgName "_backup_" (rtos month 2 0) "-" (rtos day 2 0) "-" (rtos year 2 0) "@" (rtos hour 2 0) "hr" (rtos minute 2 0) "m" (rtos second 2 0) "s" (rtos milliSecond 2 0) "ms" ".dwg")
          );end setq
          (command "_.save" saveBackup (if(/=(getvar 'cmdactive)0) "_Y") "")(command)
        );progn
      );end if
    );progn
  );end if
  (if(= nestedPointTest "Yes")
    (progn
      (setq sset (ssget "_X" '((0 . "INSERT"))))
      (if(not(= sset nil))
        (progn
          (setvar "qaflags" 1)
          (command "explode" sset "")
          (setvar "qaflags" 0)
        );progn
      );end if
    );progn
  );end if
  (if(FILE_OPEN? pointFileCSVLoc)
    (alert(strcat "File(s) currently in use, please close file(s) and try again.\n\nCheck: \n\n" pointFileCSVLoc)); "\n" pointFileTXTLoc))
    (progn
      (setvar "cmdecho" 0)
      ;(print "Do you wish to export floor support leg Center Points, Anchor Points or Both?")(princ)(terpri)
      ;(initget 0 "CenterPoints AnchorPoints Both")
      ;(setq decision (getkword "\nChoose: [CenterPoints/AnchorPoints/Both] <Centerpoints>?:"))
      ;(if(= decision nil)
      (setq decision "CenterPoints")
      ;)
      ;(if(= decision "CenterPoints")
          ;(progn(print "Only anchor plate center points will be exported for floor support.")(princ)(terpri))
        ;(if(= decision "AnchorPoints")
          ;(progn(print "Anchor plate anchor points will be exported for floor support. Center points will not be included.")(princ)(terpri))
          ;(if(= decision "Both")
            ;(progn(print "Both center points and anchor plate anchor points will be exported for floor support.")(princ)(terpri))
      ;) ) );end ifs
      (c:World_View)
      (setvar "cmdecho" 0)
      (setq sset (ssget "_X" '((0 . "MAPS_SOLID")
                               (-4 . "<OR")
                                 (300 . "Flat Strap (Rectangle)")
                                 (300 . "Flat Strap (Oval)")
                                 (300 . "Rectangular Bearer")
                                 (300 . "Wrap Round")
                                 (300 . "Flat Strap (Round)")
                                 (300 . "Belly Band")
                                 (300 . "Floor Supports Angle")
                                 (300 . "Floor Support Angle")
                                 (300 . "Floor Supports Post")
                                 (300 . "Floor Support Post")
                                 (300 . "Floor Supports Angle Round")
                                 (300 . "Floor Support Angle Round")
                                 (300 . "Floor Supports Post Round")
                                 (300 . "Floor Support Post Round")
                                 (300 . "Floor Supports Angle Double")
                                 (300 . "Floor Support Angle Double")
                                 (300 . "Floor Supports Post Double")
                                 (300 . "Floor Support Post Double")
                                 (300 . "Floor Support Angle Single")
                                 (300 . "Floor Support Post Single")
                                 (300 . "Seismic")
                                 (300 . "Equipment Seismic")
                                 (300 . "Strap Single")
                                 (300 . "Rectangular Duct Seismic")
                                 (300 . "Round Duct or Pipe Seismic")
                                 (300 . "Rectangular Seismic")
                                 (300 . "Round Seismic")
                                 (300 . "Misc Seismic")
                                 (300 . "*Clevis*")
                                 (300 . "*Pipe Roll*")
                                 (300 . "Stiffy Fig. 108")
                                 (300 . "Double Rectangular Bearer")
                                 (300 . "REFERENCE POINT")
                                 (300 . "WORK POINT")
                                 (300 . "ANCHOR POINT")
                                 (300 . "CONTROL LINE")
                                 (300 . "EQUIPMENT PAD")
                                 (300 . "FLOOR BLOCKOUT")
                                 (300 . "WALL BLOCKOUT")
                                 (300 . "BLUE BANGER")
                                 (300 . "QUICK BOLT")
                                 (300 . "Wedge Anchor")
                                 (300 . "Strap Insert")
                                 (300 . "Wire Insert")
                                 (300 . "1.0 Insert")
                                 (300 . ".875 Insert")
                                 (300 . ".75 Insert")
                                 (300 . ".625 Insert")
                                 (300 . ".5 Insert")
                                 (300 . ".375 Insert")
                                 (300 . "Supply Blockout")
                                 (300 . "Return-Transfer Blockout")
                                 (300 . "Exhaust Blockout")
                                 (300 . "Round Blockout")
                                 (300 . "EQUIPMENT PAD")
                                 (300 . "FLOOR BLOCK OUT")
                                 (300 . "WALL BLOCK OUT")
                                 (300 . "Insert")
                                 (300 . "1049")
                                 (300 . "838")
                               (-4 . "OR>")));Choose selection set
            i 0);end setq
      (OUTSIDE_LOOP_VARIABLES sset)
      (write-line "if (wildcard(item.filename,\"*Clevis*\") = 1) or (wildcard(item.filename,\"*Pipe Roll*\") = 1) or (wildcard(item.filename,\"*rectangular bearer\") = 1) or (wildcard(item.filename,\"Belly Band\") = 1) or (wildcard(item.filename,\"Double Rectangular Floor Mount\")) or (wildcard(item.filename,\"Single Rectangular Floor Mount\")) or (wildcard(item.filename,\"Round Floor Mount\")) then" writeToVBCode)
      (write-line "item.customdata[2].value = item.option[\"Drop Rod Diameter\"].value" writeToVBCode)
      (write-line "elseif (wildcard(item.filename,\"Flat Strap (Rectangle)\")) or (wildcard(item.filename,\"Flat Strap (Round)\")) or (wildcard(item.filename,\"Flat Strap (Oval)\")) or (wildcard(item.filename,\"Strap Single\")) then" writeToVBCode)
      (write-line "item.customdata[2].value = item.option[\"Bearer Width\"].value" writeToVBCode)
      (write-line "end if" writeToVBCode)
      (write-line "if item.dim[1].numvalue < 0.01 then" writeToVBCode)
      (write-line "item.dim[1].value = 0.01" writeToVBCode)
      (write-line "end if" writeToVBCode)
      (close writeToVBCode)
      (setq pointFileCSV (open pointFileCSVLoc "w"));end setq
      (write-line "POINT NUMBER, Y, X, Z, DESCRIPTION" pointFileCSV)
      (while (< i limit);Start the Loop
        (INSIDE_LOOP_VARIABLES sset i)
        (if(or allSupport trimblePoint blockout roundBlockout (wcmatch(strcase ItemSourceFileName)(strcase "EQUIPMENT PAD"))(wcmatch(strcase ItemSourceFileName)(strcase "FLOOR BLOCK OUT"))(wcmatch(strcase ItemSourceFileName)(strcase "WALL BLOCK OUT")))
          (progn
            (setq itm#A (strcat Item# "A")
                  itm#B (strcat Item# "B")
                  itm#C (strcat Item# "C")
                  itm#D (strcat Item# "D"));end setq
            (executescript vbCode SSentity)
            (INSIDE_LOOP_VARIABLES sset i)
            (if(and(not(= Automation2 ""))(not(= Automation2 nil)))(setq anchorSize (rtos(ROUND(distof Automation2 2)0.125)5))(setq Automation2 ""))
      (if rodSupport
        (setq pointDescription "Rod")
        (if strapSupport
          (setq pointDescription "Strap")
          (if postSupport
            (setq pointDescription "Post FS")
            (if angleSupport
              (setq pointDescription "Ang FS")
              (if seismic
                (setq pointDescription "Seismic" anchorSize "0")
                (if blockout
                  (setq pointDescription ItemSourceFileName)
                  (if roundBlockout
                    (setq pointDescription (strcat ItemSourceFileName " CtrPnt - " (rtos(+ dim1(* dim4 2))) " Dia"))
                    (if trimblePoint
                      (if(or(wcmatch(strcase ItemSourceFileName) "BLUE BANGER")(wcmatch(strcase ItemSourceFileName) "WEDGE ANCHOR"))
                        (setq anchorSize ItemDescription
                              pointDescription ItemSourceFileName)
                        (setq anchorSize "0"
                              pointDescription ItemSourceFileName)
                      );end if
      ) ) ) ) ) ) ) );end ifs
      (if(= pointDescription nil)(setq pointDescription ""))
      (if(or(wcmatch ItemSectionName "None")(wcmatch (strcase ItemLevel) "LEVEL"))
        (setq ItemLevel ""))
      (if(wcmatch ItemLevel "Lower")
        (setq ItemLevel "LL")
        (if(wcmatch ItemLevel "*#*")
          (setq ItemLevel (strcat "L" ItemLevel "_"))
          (setq ItemLevel "")
      ) );end if
      (if(not(=(distof anchorSize) 0))
        (progn
          (setq orgDIMZIN (getvar "DIMZIN"))
          (setvar "DIMZIN" 12)
          (setq pointDescription (strcat pointDescription ": " (rtos(distof anchorSize)2) "''"))
          (setvar "DIMZIN" orgDIMZIN)
        );progn
      );end if
      (if doubleFloorSupport
        (if(= decision "AnchorPoints")
          (progn
            (write-line (strcat "" itm#A "_1, " (rtos yA1 2 7) ", " (rtos xA1 2 7) ", " (rtos zA1 2 7) ", " pointDescription) pointFileCSV)
            (write-line (strcat "" itm#A "_2, " (rtos yA2 2 7) ", " (rtos xA2 2 7) ", " (rtos zA2 2 7) ", " pointDescription) pointFileCSV)
            (write-line (strcat "" itm#A "_3, " (rtos yA3 2 7) ", " (rtos xA3 2 7) ", " (rtos zA3 2 7) ", " pointDescription) pointFileCSV)
            (write-line (strcat "" itm#A "_4, " (rtos yA4 2 7) ", " (rtos xA4 2 7) ", " (rtos zA4 2 7) ", " pointDescription) pointFileCSV)
            (write-line (strcat "" itm#B "_1, " (rtos yB1 2 7) ", " (rtos xB1 2 7) ", " (rtos zB1 2 7) ", " pointDescription) pointFileCSV)
            (write-line (strcat "" itm#B "_2, " (rtos yB2 2 7) ", " (rtos xB2 2 7) ", " (rtos zB2 2 7) ", " pointDescription) pointFileCSV)
            (write-line (strcat "" itm#B "_3, " (rtos yB3 2 7) ", " (rtos xB3 2 7) ", " (rtos zB3 2 7) ", " pointDescription) pointFileCSV)
            (write-line (strcat "" itm#B "_4, " (rtos yB4 2 7) ", " (rtos xB4 2 7) ", " (rtos zB4 2 7) ", " pointDescription) pointFileCSV)
            ;(command "._circle" (list xA1 yA1 zA1) "1" "")
            ;(command "._circle" (list xA2 yA2 zA2) "1" "")
            ;(command "._circle" (list xA3 yA3 zA3) "1" "")
            ;(command "._circle" (list xA4 yA4 zA4) "1" "")
            ;(command "._circle" (list xB1 yB1 zB1) "1" "")
            ;(command "._circle" (list xB2 yB2 zB2) "1" "")
            ;(command "._circle" (list xB3 yB3 zB3) "1" "")
            ;(command "._circle" (list xB4 yB4 zB4) "1" "")
          );end progn
          (if(= decision "CenterPoints")
            (progn
              (write-line (strcat "" itm#A ", " (rtos yA 2 7) ", " (rtos xA 2 7) ", " (rtos zA 2 7) ", " pointDescription " LegCntr") pointFileCSV)
              (write-line (strcat "" itm#B ", " (rtos yB 2 7) ", " (rtos xB 2 7) ", " (rtos zB 2 7) ", " pointDescription " LegCntr") pointFileCSV)
              ;(command "._circle" (list xA yA zA) "2" "")
              ;(command "._circle" (list xB yB zB) "2" "")
            );end progn
            (if(= decision "Both")
              (progn
                (write-line (strcat "" itm#A ", " (rtos yA 2 7) ", " (rtos xA 2 7) ", " (rtos zA 2 7) ", " pointDescription " LegCntr") pointFileCSV)
                (write-line (strcat "" itm#B ", " (rtos yB 2 7) ", " (rtos xB 2 7) ", " (rtos zB 2 7) ", " pointDescription " LegCntr") pointFileCSV)
                ;(command "._circle" (list xA yA zA) "2" "")
                ;(command "._circle" (list xB yB zB) "2" "")
                (write-line (strcat "" itm#A "_1, " (rtos yA1 2 7) ", " (rtos xA1 2 7) ", " (rtos zA1 2 7) ", " pointDescription) pointFileCSV)
                (write-line (strcat "" itm#A "_2, " (rtos yA2 2 7) ", " (rtos xA2 2 7) ", " (rtos zA2 2 7) ", " pointDescription) pointFileCSV)
                (write-line (strcat "" itm#A "_3, " (rtos yA3 2 7) ", " (rtos xA3 2 7) ", " (rtos zA3 2 7) ", " pointDescription) pointFileCSV)
                (write-line (strcat "" itm#A "_4, " (rtos yA4 2 7) ", " (rtos xA4 2 7) ", " (rtos zA4 2 7) ", " pointDescription) pointFileCSV)
                (write-line (strcat "" itm#B "_1, " (rtos yB1 2 7) ", " (rtos xB1 2 7) ", " (rtos zB1 2 7) ", " pointDescription) pointFileCSV)
                (write-line (strcat "" itm#B "_2, " (rtos yB2 2 7) ", " (rtos xB2 2 7) ", " (rtos zB2 2 7) ", " pointDescription) pointFileCSV)
                (write-line (strcat "" itm#B "_3, " (rtos yB3 2 7) ", " (rtos xB3 2 7) ", " (rtos zB3 2 7) ", " pointDescription) pointFileCSV)
                (write-line (strcat "" itm#B "_4, " (rtos yB4 2 7) ", " (rtos xB4 2 7) ", " (rtos zB4 2 7) ", " pointDescription) pointFileCSV)
                ;(command "._circle" (list xA1 yA1 zA1) "1" "")
                ;(command "._circle" (list xA2 yA2 zA2) "1" "")
                ;(command "._circle" (list xA3 yA3 zA3) "1" "")
                ;(command "._circle" (list xA4 yA4 zA4) "1" "")
                ;(command "._circle" (list xB1 yB1 zB1) "1" "")
                ;(command "._circle" (list xB2 yB2 zB2) "1" "")
                ;(command "._circle" (list xB3 yB3 zB3) "1" "")
                ;(command "._circle" (list xB4 yB4 zB4) "1" "")
              );end progn
        ) ) ) );end ifs
        (if doubleHangerSupport
          (progn
            (write-line (strcat "" itm#A ", " (rtos yA 2 7) ", " (rtos xA 2 7) ", " (rtos zA 2 7) ", " pointDescription) pointFileCSV)
            (write-line (strcat "" itm#B ", " (rtos yB 2 7) ", " (rtos xB 2 7) ", " (rtos zB 2 7) ", " pointDescription) pointFileCSV)
            ;(command "._circle" (list xA yA zA) "2" "")
            ;(command "._circle" (list xB yB zB) "2" "")
          );end progn
          (if(or singleHangerSeismic trimblePoint)
            (progn
              (write-line (strcat "" itm#A ", " (rtos yA 2 7) ", " (rtos xA 2 7) ", " (rtos zA 2 7) ", " pointDescription) pointFileCSV)
              ;(write-line (strcat itm#A ", " (rtos yA 2 7) ", " (rtos xA 2 7) ", " (rtos zA 2 7) ", " pointDescription) pointFileTXT)
              ;(command "._circle" (list xA yA zA) "2" "")
            );progn
            (if singleFloorSupport
              (if(= decision "AnchorPoints")
                (progn
                  (write-line (strcat "" itm#A "_1, " (rtos yA1 2 7) ", " (rtos xA1 2 7) ", " (rtos zA1 2 7) ", " pointDescription) pointFileCSV)
                  (write-line (strcat "" itm#A "_2, " (rtos yA2 2 7) ", " (rtos xA2 2 7) ", " (rtos zA2 2 7) ", " pointDescription) pointFileCSV)
                  (write-line (strcat "" itm#A "_3, " (rtos yA3 2 7) ", " (rtos xA3 2 7) ", " (rtos zA3 2 7) ", " pointDescription) pointFileCSV)
                  (write-line (strcat "" itm#A "_4, " (rtos yA4 2 7) ", " (rtos xA4 2 7) ", " (rtos zA4 2 7) ", " pointDescription) pointFileCSV)
                  ;(write-line (strcat itm#A "_1, " (rtos yA1 2 7) ", " (rtos xA1 2 7) ", " (rtos zA1 2 7) ", " pointDescription) pointFileTXT)
                  ;(write-line (strcat itm#A "_2, " (rtos yA2 2 7) ", " (rtos xA2 2 7) ", " (rtos zA2 2 7) ", " pointDescription) pointFileTXT)
                  ;(write-line (strcat itm#A "_3, " (rtos yA3 2 7) ", " (rtos xA3 2 7) ", " (rtos zA3 2 7) ", " pointDescription) pointFileTXT)
                  ;(write-line (strcat itm#A "_4, " (rtos yA4 2 7) ", " (rtos xA4 2 7) ", " (rtos zA4 2 7) ", " pointDescription) pointFileTXT)
                  ;(command "._circle" (list xA1 yA1 zA1) "1" "")
                  ;(command "._circle" (list xA2 yA2 zA2) "1" "")
                  ;(command "._circle" (list xA3 yA3 zA3) "1" "")
                  ;(command "._circle" (list xA4 yA4 zA4) "1" "")
                );end progn
                (if(= decision "CenterPoints")
                  (progn
                    (write-line (strcat "" itm#A ", " (rtos yA 2 7) ", " (rtos xA 2 7) ", " (rtos zA 2 7) ", " pointDescription " LegCntr") pointFileCSV)
                  );end progn
                  (if(= decision "Both")
                    (progn
                      (write-line (strcat "" itm#A ", " (rtos yA 2 7) ", " (rtos xA 2 7) ", " (rtos zA 2 7) ", " pointDescription " LegCntr") pointFileCSV)
                      ;(command "._circle" (list xA yA zA) "2" "")
                      (write-line (strcat "" itm#A "_1, " (rtos yA1 2 7) ", " (rtos xA1 2 7) ", " (rtos zA1 2 7) ", " pointDescription) pointFileCSV)
                      (write-line (strcat "" itm#A "_2, " (rtos yA2 2 7) ", " (rtos xA2 2 7) ", " (rtos zA2 2 7) ", " pointDescription) pointFileCSV)
                      (write-line (strcat "" itm#A "_3, " (rtos yA3 2 7) ", " (rtos xA3 2 7) ", " (rtos zA3 2 7) ", " pointDescription) pointFileCSV)
                      (write-line (strcat "" itm#A "_4, " (rtos yA4 2 7) ", " (rtos xA4 2 7) ", " (rtos zA4 2 7) ", " pointDescription) pointFileCSV)
                    );end progn
              ) ) );end ifs
      ) ) );end ifs
      (if blockout
        (progn
          (write-line (strcat "" itm#A ", " (rtos yA 2 7) ", " (rtos xA 2 7) ", " (rtos zA 2 7) ", " pointDescription) pointFileCSV)
          (write-line (strcat "" itm#B ", " (rtos yB 2 7) ", " (rtos xB 2 7) ", " (rtos zB 2 7) ", " pointDescription) pointFileCSV)
          (write-line (strcat "" itm#C ", " (rtos yC 2 7) ", " (rtos xC 2 7) ", " (rtos zC 2 7) ", " pointDescription) pointFileCSV)
          (write-line (strcat "" itm#D ", " (rtos yD 2 7) ", " (rtos xD 2 7) ", " (rtos zD 2 7) ", " pointDescription) pointFileCSV)
        );progn
          (if roundBlockout
            (progn
              (write-line (strcat "" itm#A ", " (rtos yA 2 7) ", " (rtos xA 2 7) ", " (rtos zA 2 7) ", " pointDescription) pointFileCSV)
              ;(write-line (strcat itm#A ", " (rtos yA 2 7) ", " (rtos xA 2 7) ", " (rtos zA 2 7) ", " pointDescription) pointFileTXT)
              ;(command "._circle" (list xA yA zA) "2" "")
            );progn
      ) );end ifs
      (setq xA nil
            yA nil
            zA nil
            xB nil
            yB nil
            zB nil
            xA1 nil
            yA1 nil
            zA1 nil
            xB1 nil
            yB1 nil
            zB1 nil
            xA2 nil
            yA2 nil
            zA2 nil
            xB2 nil
            yB2 nil
            zB2 nil
            xA3 nil
            yA3 nil
            zA3 nil
            xB3 nil
            yB3 nil
            zB3 nil
            xA4 nil
            yA4 nil
            zA4 nil
            xB4 nil
            yB4 nil
            zB4 nil);end setq
        );end progn
      );end if
            (setq i (1+ i))
    );end while
    (close pointFileCSV)
    ;(close pointFileTXT)
  (terpri)
  (princ (strcat "Check: " pointFileCSVLoc))(princ)(terpri)
  (princ (strcat "Check: " saveBackup))(princ)(terpri)
    );progn
  );end if
  (vl-file-delete vbCode)
  (setvar 'filedia 1)
  (setq nestedPointTest nil)
(END_ROUTINE));end defun
;**************************************************************************************************************************************************
(defun c:Create_2D (/)
  ; CREATE A 2D OF THE DRAWING
  (vl-load-com)
  (OUTSIDE_LOOP_VARIABLES sset)
  (setvar "cmdecho" 0)
  (if(= scaleTest ni
	l)
    (progn
      (print "Do you want your 2D drawing scaled down?")(princ)(terpri)
      (print "1: Yes - Drawing will be scaled.")(princ)(terpri)
      (print "2: No - Drawing will not be scaled.")(princ)(terpri)
      (initget 0 "Yes No")
      (setq scaleTest (getkword "\nChoose: [Yes/No] <No>?:"))
      (if(= scaleTest nil)
        (setq scaleTest "No")
      );end if
    );end progn
  );end if
  (command "_qsave" "")
  (if(not(= dwgLink nil))
    (progn
      (STRING_SPLIT "/" dwgLink)
      (setq folderString (strcat nth0 "/" nth1 "/07)FABRICATION/03) SHEET METAL/"))
      (if(vl-file-directory-p folderString)
        (progn
          (setq 2DFileName (vl-string-translate "/" "\\" (strcat folderString dwgName "_2D.dwg"))
                saveBackup (vl-string-translate "/" "\\" (strcat folderString dwgName "_C2D;Backup_" (rtos month 2 0) "-" (rtos day 2 0) "-" (rtos year 2 0) "@" (rtos hour 2 0) ";" (rtos minute 2 0) ";" (rtos second 2 0) ";" (rtos milliSecond 2 0) ".dwg"))
          );end setq
          (command "_.save" saveBackup (if(/=(getvar 'cmdactive)0) "_Y") "")(command)
        );progn
        (progn
          (setq 2DFileName (vl-string-translate "/" "\\" (strcat dwgDirectory dwgName "_2D.dwg"))
                saveBackup (vl-string-translate "/" "\\" (strcat dwgDirectory dwgName "_C2D;Backup_" (rtos month 2 0) "-" (rtos day 2 0) "-" (rtos year 2 0) "@" (rtos hour 2 0) ";" (rtos minute 2 0) ";" (rtos second 2 0) ";" (rtos milliSecond 2 0) ".dwg"))
          );end setq
          (command "_.save" saveBackup (if(/=(getvar 'cmdactive)0) "_Y") "")(command)
        );progn
      );end if
    );progn
  );end if
  (setvar 'filedia 0)
  (vla-saveas(vla-get-ActiveDocument(vlax-get-Acad-Object))2DFileName)
  (c:World_View)
  (command "-purge" "R" "*" "N")
  (command "-purge" "Z" "")
  (setq purgeCount 0
        purgeLimit 10);end setq
  (while (< purgeCount purgeLimit)
    (command "-purge" "a" "*" "n")
    (setq purgeCount (1+ purgeCount));end setq
  );end while
  (command "_layer" "_unlock" "*" "")(command)
      (setq xrefBlock (tblnext "BLOCK" T))
      (while xrefBlock
        (setq xrefBlockName (cdr(assoc 2 xrefBlock)))
        (if
          (and
            (=(logand(cdr(assoc 70 xrefBlock))32)32)
            (=(logand(cdr(assoc 70 xrefBlock))4)4)
          );and
          (progn
            (vl-cmdf "bindtype" "1")
            (vl-cmdf "_.xref" "_unload" xrefBlockName)
            (vl-cmdf "_.xref" "_reload" xrefBlockName)
            (vl-cmdf "_.xref" "_bind" xrefBlockName)
          );progn
          (vl-cmdf "_.xref" "_detach" xrefBlockName)
        );end if
        (setq xrefBlock (tblnext "BLOCK"))
      ); end while
      (vlax-for block
        (vla-get-Blocks
          (vla-get-ActiveDocument (vlax-get-acad-object))
        );vla-get-blocks
        (or
          (wcmatch (vla-get-Name block) "`**_Space*")
          (vla-put-explodable block :vlax-true)
        );or
      );vlax-for
      (setq sset (ssget "_X" '((0 . "INSERT"))))
      (if(not(= sset nil))
        (progn
          (setvar "qaflags" 1)
          (command "explode" sset "")
          (setvar "qaflags" 0)
        );progn
      );end if
      (setq sset (ssget "_X" '((0 . "MAPS_SOLID")))
            i 0);end setq
  (if(not(= sset nil))
    (progn
      (removemaptext sset 127)
      (while (< i limit);Start the Loop
        (INSIDE_LOOP_VARIABLES sset i)
        (if(or allHanger (not(or(wcmatch (strcase ItemService) "*COMBUSTION*")
                                (wcmatch (strcase ItemService) "*EXHAUST*")
                                (wcmatch (strcase ItemService) "*OUTSIDE*")
                                (wcmatch (strcase ItemService) "*RETURN*")
                                (wcmatch (strcase ItemService) "*SUPPLY*")
                                (wcmatch (strcase ItemService) "*TRANSFER*"))))
          (command "erase" SSEntity "")
        );end if
        (setq i (1+ i))
      );end while
      (command "create2d" sset "")
      (command "erase" sset "")
    );progn
    (princ "No 3D item found in the drawing")
  );end if
  (setq sset (ssget "X"))
  (if(not(= sset nil))
    (progn
      (command "pselect" sset "")
      (SUPERFLATTEN)
      (command "-purge" "R" "*" "N")
      (command "-purge" "Z" "")
      (setq purgeCount 0
            purgeLimit 10);end setq
      (while (< purgeCount purgeLimit)
        (command "-purge" "a" "*" "n")
        (setq purgeCount (1+ purgeCount));end setq
      );end while
      (setq sset (ssget "_X"))
      (command "-overkill" "")
      (command "-overkill" "")
      (if(wcmatch scaleTest "Yes")
        (command "scale" sset "" "0,0,0" "0.083333")
        (setq scaleTest nil)
      );end if
      (command "planview")
      (setvar 'filedia 1)
      (setvar "cmdecho" 1)
      (command "_qsave" "")
      (terpri)(princ (strcat "Check: " 2DFileName))(princ)
      (terpri)(princ (strcat "Check: " saveBackup))(princ)(terpri)
    );progn
    (princ "This is an empty drawing...")
  );end if
  (setq scaleTest nil)
  (princ)
(END_ROUTINE));end defun
;**************************************************************************************************************************************************
(defun c:List_All_Functions ( / a b c d ) (vl-load-com)
    (if (setq b (open (setq a (vl-filename-mktemp nil (getvar 'DWGPREFIX) ".txt")) "w"))
        (progn
            (foreach c
                (acad_strlsort
                    (vl-remove-if-not
                        (function
                            (lambda ( d )
                                (member (type (eval (read d))) '(SUBR EXRXSUBR))
                            )
                        )
                        (atoms-family 1)
                    )
                )
                (write-line c b)
            )
            (close b) (startapp "notepad" a)
        )
    )
    (princ)
(END_ROUTINE));end defun
;**************************************************************************************************************************************************
(defun c:pickem (/ pick pickSS pickL1 pickL2)
(setq pick (getstring T "\nEnter something: "))
(setq pickSS (ssget "x"))
(setq pickL1 (sslength pickSS))
(sssetfirst nil pickSS)
;currently set up to pick by piece number
(setq pickSS (ssget (mapfilter (strcat "\"#20 = \"" pick "\""))))
(setq pickL2 (sslength pickSS))
(if (> pickL1 pickL2)
(progn
(command "zoom" "object" pickSS "")
(setq pickSS (ssget "P"))
(sssetfirst nil pickSS)
)
(progn
(command "select" "none" "")
(princ "Nothing Found!")
)
)
(princ)
(END_ROUTINE));end defun
;**************************************************************************************************************************************************
(defun c:Search_Specification (/ pick specSS specL1 specL2)
  (setq spec (getstring T "\nEnter with this format <\"Spec-Group: Specification\">: ")
        specSS (ssget "x")
        specL1 (sslength specSS));end setq
  (sssetfirst nil specSS)
;currently set up to pick by piece number
  (setq specSS (ssget (mapfilter (strcat "\"#19 = \"" spec "\"")))
        specL2 (sslength specSS));end setq
  (if (> specL1 specL2)
    (progn
      (command "zoom" "object" specSS "")
      (setq specSS (ssget "P"))
      (sssetfirst nil specSS)
      (command "pselect" specSS "")
      (command "chspec")
    );end progn
    (progn
      (command "select" "none" "")
      (princ "Nothing Found!")
    );end progn
  );end if
  (princ)
(END_ROUTINE));end defun
;**************************************************************************************************************************************************
(defun c:Get_Keyboard_ASCII_Character ( / code)
  (prompt "\nEnter a single character: ")
  
  (setq code (grread))

  (if (= 2 (car code))
    (progn
      (prompt (strcat "\nCharacter entered was: " (chr (cadr code))))
      (prompt (strcat "\nASCII code: " (itoa (cadr code))))
    )
    (prompt "\nInput was not from the keyboard.")
  )
 (princ)
(END_ROUTINE));end defun
;**************************************************************************************************************************************************
(defun c:Mark_Support_Point_Locations (/)
  ; label points
  (vl-load-com)
  (setvar "cmdecho" 0)
  (c:World_View)
  (setq sset (ssget "_X" '((0 . "MAPS_SOLID")
                               (-4 . "<OR")
                                 (300 . "Flat Strap (Rectangle)")
                                 (300 . "Flat Strap (Oval)")
                                 (300 . "Rectangular Bearer")
                                 (300 . "Wrap Round")
                                 (300 . "Flat Strap (Round)")
                                 (300 . "Belly Band")
                                 (300 . "Floor Supports Angle")
                                 (300 . "Floor Support Angle")
                                 (300 . "Floor Supports Post")
                                 (300 . "Floor Support Post")
                                 (300 . "Floor Supports Angle Round")
                                 (300 . "Floor Support Angle Round")
                                 (300 . "Floor Supports Post Round")
                                 (300 . "Floor Support Post Round")
                                 (300 . "Floor Supports Angle Double")
                                 (300 . "Floor Support Angle Double")
                                 (300 . "Floor Supports Post Double")
                                 (300 . "Floor Support Post Double")
                                 (300 . "Floor Support Angle Single")
                                 (300 . "Floor Support Post Single")
                                 (300 . "Equipment Seismic")
                                 (300 . "Strap Single")
                                 (300 . "Rectangular Duct Seismic")
                                 (300 . "Round Duct or Pipe Seismic")
                                 (300 . "Rectangular Seismic")
                                 (300 . "Round Seismic")
                                 (300 . "Misc Seismic")
                                 (300 . "*Clevis*")
                                 (300 . "*Pipe Roll*")
                                 (300 . "Stiffy Fig. 108")
                                 (300 . "Double Rectangular Bearer")
                                 (300 . "REFERENCE POINT")
                                 (300 . "WORK POINT")
                                 (300 . "ANCHOR POINT")
                                 (300 . "CONTROL LINE")
                                 (300 . "EQUIPMENT PAD")
                                 (300 . "FLOOR BLOCKOUT")
                                 (300 . "WALL BLOCKOUT")
                                 (300 . "BLUE BANGER")
                                 (300 . "QUICK BOLT")
                                 (300 . "Wedge Anchor")
                                 (300 . "Strap Insert")
                                 (300 . "Wire Insert")
                                 (300 . "1.0 Insert")
                                 (300 . ".875 Insert")
                                 (300 . ".75 Insert")
                                 (300 . ".625 Insert")
                                 (300 . ".5 Insert")
                                 (300 . ".375 Insert")
                                 (300 . "Supply Blockout")
                                 (300 . "Return-Transfer Blockout")
                                 (300 . "Exhaust Blockout")
                                 (300 . "Round Blockout")
                                 (300 . "EQUIPMENT PAD")
                                 (300 . "FLOOR BLOCK OUT")
                                 (300 . "WALL BLOCK OUT")
                                 (300 . "Insert")
                               (-4 . "OR>")));Choose selection set
        i 0)
  (OUTSIDE_LOOP_VARIABLES sset)
    (while (< i limit);Start the Loop
      (INSIDE_LOOP_VARIABLES sset i)
        (setq AOI "6"
              coordinatesA (list xA yA zA)
              coordinatesB (list xB yB zB)
              pointlocations (ssadd));end setq
      (command "layer" "make" "M-AMC-SUPT-POIN-TLOC-ATIO-NS" "")
      (if doubleSupportAll
        (progn
          (initcommandversion 2)
          (command "._circle" coordinatesA "D" AOI)
          (ssadd (entlast) pointlocations)
          (command "._circle" coordinatesB "D" AOI)
          (ssadd (entlast) pointlocations)
          (initcommandversion 1)
	);end progn
        (if singleGravitySeismic
          (progn
            (initcommandversion 2)
            (command "._circle" coordinatesA "D" AOI)
            (ssadd (entlast) pointlocations)
            (initcommandversion 1)
          );end progn
      ) );end ifs 
            (setq i (1+ i));increment the sub loop
      );end while
  (command "copyclip" pointlocations "")
  (command "pselect" pointlocations "")
  (princ "Layout point location labels are now copied to your clipboard: paste them in a new drawing using \"PO\" (Paste_to_Original_Coordinates) if needed.")(terpri)
  (princ)
(END_ROUTINE))
;**************************************************************************************************************************************************
(defun c:Label_Layout_Points (/)
  ; label points
  (vl-load-com)
  (setvar "cmdecho" 0)
  (c:World_View)
  (print "Are you anchoring strap to rod inserts on this floor?")(princ)(terpri)
  (initget 0 "Yes No")
  (setq decision (getkword "\nChoose: [Yes/No] <No>?:"))
  (if (= decision nil)
    (setq decision "No"))
  (setq sset (ssget "_X" '((0 . "MAPS_SOLID")));Choose selection set
        i 0
	hanger (ssadd)
        pointlocations (ssadd))
  (OUTSIDE_LOOP_VARIABLES sset)
    (while (< i limit);Start the Loop
      (INSIDE_LOOP_VARIABLES sset i)
      (if allHanger (ssadd ent hanger));end if
          (setq i (1+ i));increment the main loop
    );endwhile
  (write-line "if ((wildcard(item.filename,\"*Clevis*\") = 1) or (wildcard(item.filename,\"*rectangular bearer\") = 1) or (wildcard(item.filename,\"Belly Band\") = 1) or (wildcard(item.filename,\"Double Rectangular Floor Mount\")) or (wildcard(item.filename,\"Single Rectangular Floor Mount\")) or (wildcard(item.filename,\"Round Floor Mount\"))) then" writeToVBCode)
  (write-line "item.customdata[2].value = item.option[\"Drop Rod Diameter\"].value" writeToVBCode)
  (write-line "elseif (wildcard(item.filename,\"Wrap Round\")) then" writeToVBCode)
  (write-line "item.customdata[2].value = item.dim[3].value" writeToVBCode)
  (write-line "elseif (wildcard(item.filename,\"Flat Strap (Rectangle)\")) or (wildcard(item.filename,\"Flat Strap (Round)\")) or (wildcard(item.filename,\"Strap Single\")) then" writeToVBCode)
  (write-line "item.customdata[2].value = item.option[\"Bearer Width\"].value" writeToVBCode)
  (write-line "elseif (wildcard(item.filename,\"Angle Roof Support\")) then" writeToVBCode)
  (write-line "item.customdata[2].value = item.dim[\"Angle Size\"].value" writeToVBCode)
  (write-line "end if" writeToVBCode)
(close writeToVBCode)
(if(not(= hanger nil))
    (progn
    (setq h 0
          hsublimit (sslength hanger)
          scaleFactor ".33");end setq
    (while (< h hsublimit);Start the sub loop
      (INSIDE_LOOP_VARIABLES hanger h)
	(if(wcmatch ItemService "*COMBUSTION*")(setq servicePrefix "C-")
          (if(wcmatch ItemService "*EXHAUST*")(setq servicePrefix "E-")
            (if(wcmatch ItemService "*OUTSIDE*")(setq servicePrefix "O-")
              (if(wcmatch ItemService "*RETURN*")(setq servicePrefix "R-")
                (if(wcmatch ItemService "*SUPPLY*")(setq servicePrefix "S-")
                  (if(wcmatch ItemService "*TRANSFER*")(setq servicePrefix "T-")
                  (if(not(or(wcmatch ItemService "*COMBUSTION*")(wcmatch ItemService "*EXHAUST*")(wcmatch ItemService "*OUTSIDE*")(wcmatch ItemService "*RETURN*")(wcmatch ItemService "*SUPPLY*")(wcmatch ItemService "*TRANSFER*")))(setq servicePrefix "")
        ) ) ) ) ) ) );end ifs
      (command "pselect" ent "")
      (executescript vbCode)
      (if(= Automation2 "")
        (executescript vbCode SSentity));end if
      (if(or(wcmatch Automation2 "*.13")(wcmatch Automation2 "*.125"))
        (setq Automation2 "1/8\"")
        (if(wcmatch Automation2 "*.25")
          (setq Automation2 "1/4\"")
          (if(or(wcmatch Automation2 "*.38")(wcmatch Automation2 "*.375"))
            (setq Automation2 "3/8\"")
            (if(wcmatch Automation2 "*.5")
              (setq Automation2 "1/2\"")
              (if(or(wcmatch Automation2 "*.63")(wcmatch Automation2 "*.625"))
                (setq Automation2 "5/8\"")
                (if(wcmatch Automation2 "*.75")
                  (setq Automation2 "3/4\"")
                  (if(or(wcmatch Automation2 "*.88")(wcmatch Automation2 "*.875"))
                    (setq Automation2 "7/8\"")
                    (if(wcmatch Automation2 "1.00")
                      (setq Automation2 "1\"")
      ) ) ) ) ) ) ) );end ifs
    (if singleGravity
      (setq xA c2x
            yA c2y
            zA c2z)
      (if doubleSupportAll
        (setq xA c2x
              yA c2y
              zA c2z
              xB c3x
              yB c3y
              zB c3z)
        (if(wcmatch ItemSourceFileName "Seismic Rectangular")
          (setq xA c4x
                yA c4y
                zA c4z)
          (if(wcmatch ItemSourceFileName "Seismic")
            (setq xA c13x
                  yA c13y
                  zA c13z)
            (if angleSupport
              (setq xA c12x
                    yA c12y
                    zA c12z
                    xB c14x
                    yB c14y
                    zB c14z)
    ) ) ) ) );end ifs
      (if rodSupport
        (setq pointDescription "Ro: ")
        (if strapSupport
          (setq pointDescription "St: ")
          (if seismic
            (setq pointDescription "Se: ")
      ) ) );end ifs
      (if seismic
        (setq AOI "9")
        (setq AOI "6")
      );end if 
      (setq coordinatesA (list xA yA zA)
            coordinatesA+ (list (- xA 3) (+ yA 1) zA));end setq
      (if doubleSupportAll
        (setq coordinatesB (list xB yB zB)
              coordinatesB+ (list (- xB 3) (+ yB 1) zB));end setq
      );end if
      (if(wcmatch pointDescription "St: ")
        (if(= decision "No")
          (setq Description (strcat servicePrefix pointDescription Automation2));end setq
          (setq Description (strcat servicePrefix pointDescription "3/8\""));end setq
        );end if
        (if(wcmatch pointDescription "Se: ")
          (setq Description (strcat servicePrefix pointDescription "1/2"));end setq
          (setq Description (strcat servicePrefix pointDescription Automation2));end setq
      ) );end ifs
      (COMMAND "LAYER" "SET" "_TEXT" "")
      (if doubleSupportAll
        (progn
          (initcommandversion 2)
          (command "._circle" coordinatesA "D" AOI)
          (setq lastent (entlast))
          (ssadd lastent pointlocations)
          (command "._circle" coordinatesB "D" AOI)
          (setq lastent (entlast))
          (ssadd lastent pointlocations)
          (command "-mtext" coordinatesA+ coordinatesA Description "" "")
          (setq lastent (entlast))
	  (command "scale" lastent "" coordinatesA+ scaleFactor)
          (ssadd lastent pointlocations)
          (command "-mtext" coordinatesB+ coordinatesB Description "" "")
          (setq lastent (entlast))
	  (command "scale" lastent "" coordinatesB+ scaleFactor)
          (ssadd lastent pointlocations)
          (initcommandversion 1)
	  );end progn
        (if singleGravitySeismic
          (progn
          (initcommandversion 2)
          (command "._circle" coordinatesA "D" AOI)
          (setq lastent (entlast))
          (ssadd lastent pointlocations)
          (command "-mtext" coordinatesA+ coordinatesA Description "" "")
          (setq lastent (entlast))
	  (command "scale" lastent "" coordinatesA+ scaleFactor)
          (ssadd lastent pointlocations)
          (initcommandversion 1)
	  );end progn
        ) );end ifs 

            (setq h (1+ h));increment the sub loop
      );end while
    );end progn
  );end if
  (vl-file-delete vbCode)
  (command "copyclip" pointlocations "")
  (command "erase" pointlocations "")
  (princ "Layout point location labels are now copied to your clipboard: paste them in a new drawing using \"PO\" (Paste_to_Original_Coordinates)")(terpri)
  (setvar "cmdecho" 1)
  (princ)
(END_ROUTINE));end defun
;**************************************************************************************************************************************************
;turn off all xref layers
(defun c:XRF ()
  (command "_.-layer" "_off" "*|*" "")
  (princ)
);end defun
;**************************************************************************************************************************************************
(defun c:XRLL ()
  (command "_.-layer" "_lock" "*|*" "")
  (princ)
);end defun
;**************************************************************************************************************************************************
(defun c:XRUL ()
  (command "_.-layer" "_unlock" "*|*" "")
  (princ)
);end defun
;**************************************************************************************************************************************************
;UNLOAD ALL XREFS
(defun c:XRU ()
  (command "_.-xref" "_UNLOAD" "*")
  (princ)
);end defun
;**************************************************************************************************************************************************
;RELOAD ALL XREFS
(defun c:XRR ()
  (command "_.-xref" "_RELOAD" "*" )
  (princ)
);end defun
;**************************************************************************************************************************************************
(defun c:ZO ()
  ;;;; ZO even from section cut
  (command "LASTVIEW")
  (command "ucs" "w")
  (command "pselect" "p" "")
  (command "zoom" "object")
  (princ)
(END_ROUTINE));end defun
;**************************************************************************************************************************************************
(defun c:UPDATE_JOB_INFO ()
  (setvar "cmdecho" 0)
  (setq i 0
        sset (ssget "_X" '((0 . "MAPS_SOLID")))
  );end setq
  (OUTSIDE_LOOP_VARIABLES sset)
  (UpdateJobData 10 jobName)
  (UpdateJobData 11 job#)
  (UpdateJobData 14 jobCreationDate)
  (if(not(= dwgLevel nil))
    (UpdateJobData 2 dwgLevel)
    (progn
      (setq dwgLevel (getstring T "\nPlease enter this drawing's floor/level #:"))
      (if(not(= dwgLevel ""))
        (UpdateJobData 2 dwgLevel)
      );end if
    );end progn
  );end if
  (setq foremanName (getstring T "\nPlease enter the job foreman's name:"))
  (if(not(= foremanName ""))
    (progn
      (UpdateJobData 12 foremanName)
      (setq foremanContact (getstring T "\nPlease enter the job foreman's contact #:"))
      (if(not(= foremanContact ""))
        (UpdateJobData 13 foremanContact)
      );end if
    );end progn
  );end if
  (setq decision nil)
  (initget 0 "Yes No")
  (setq decision (getkword "\nDo you wish to update all items in the drawing? Depending on drawing size this may take a few minutes: [Yes/No] <No>?:"))
  (if(= decision nil)
    (setq decision "No"))
  (if(= decision "Yes")
    (progn
    (alert "I will be checking the activity #s and ItemCIDs of each item and updating as needed. \nThis may take a few minutes, please wait...")
    (while(< i limit)
    (INSIDE_LOOP_VARIABLES sset i)
    (if(or(wcmatch(strcase ItemServiceType)(strcase "*Equipment*"))
        (wcmatch(strcase ItemSourceFileName)(strcase "*Diffuser*"))
        (wcmatch(strcase ItemSourceFileName)(strcase "*Register*"))
        (wcmatch(strcase ItemSourceFileName)(strcase "*Grille*"))
        (wcmatch(strcase ItemSourceFileName)(strcase "*Titus*")))
    (setq Activity# "75")
    (if(or(wcmatch(strcase ItemServiceType)(strcase "*Fire Damper*"))
          (wcmatch(strcase ItemDescription)(strcase "*Canvas*"))
          (wcmatch(strcase ItemDescription)(strcase "*Access Door*"))
          (wcmatch(strcase ItemDescription)(strcase "*Damper Sleeve*"))
          (wcmatch(strcase ItemDescription)(strcase "*Plate*"))
          (and(wcmatch(strcase ItemSourceFileName)(strcase "*Angle*"))(not(wcmatch(strcase ItemSourceFileName)(strcase "*Rectangle*"))))
          (wcmatch(strcase ItemSourceFileName)(strcase "*Can*")))
      (setq Activity# "302")
      (if(or allSupport (wcmatch(strcase ItemServiceType)(strcase "*Hanger*")))
        (setq Activity# "303")
    (if(and(wcmatch(strcase ItemServiceType)(strcase "*Ductboard*"))
          (wcmatch(strcase ItemSourceFileName)(strcase "*Straight*")))
      (setq Activity# "304")
    (if(and(wcmatch(strcase ItemServiceType)(strcase "*Ductboard*"))
          (not(wcmatch(strcase ItemSourceFileName)(strcase "*Straight*"))))
      (setq Activity# "305")
        (if(and(not(or(wcmatch(strcase ItemService)(strcase "*Weld*"))(wcmatch(strcase ItemServiceType)(strcase "*Equipment*"))))
	  (or
           (and(wcmatch(strcase ItemDescription)(strcase "Straight"))
               (wcmatch(strcase c1Spec)(strcase "TDF"))
               (= ItemLengthAngle 56))
           (and(wcmatch(strcase ItemDescription)(strcase "Straight"))
               (or(wcmatch(strcase c1Spec)(strcase "Stand S&D"))
                  (wcmatch(strcase c1Spec)(strcase "Flat S&D")))
               (= ItemLengthAngle 59))
          ))
          (setq Activity# "310")
          (if(and(wcmatch(strcase ItemSourceFileName)(strcase "*SPIRAL"))(not(or(wcmatch(strcase ItemService)(strcase "*Weld*"))(wcmatch(strcase ItemServiceType)(strcase "*Equipment*")))))
            (setq Activity# "312")
            (if(and(not(or(wcmatch(strcase ItemService)(strcase "*Weld*"))(wcmatch(strcase ItemServiceType)(strcase "*Equipment*"))))
               (or
               (wcmatch(strcase ItemSourceFileName)(strcase "*Pipe*"))
               (and
               (= ItemLengthAngle 18)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*8/6/6*"))
                  (wcmatch(strcase ItemDescription)(strcase "*10/8/6*"))
                  (wcmatch(strcase ItemDescription)(strcase "*10/8/8*"))
                  (wcmatch(strcase ItemDescription)(strcase "*12/8/6*"))
                  (wcmatch(strcase ItemDescription)(strcase "*12/8/8*"))
                  (wcmatch(strcase ItemDescription)(strcase "*12/10/6*"))
                  (wcmatch(strcase ItemDescription)(strcase "*12/10/8*"))
                  (wcmatch(strcase ItemDescription)(strcase "*12/10/10*"))
                  (wcmatch(strcase ItemDescription)(strcase "*14/10/8*"))
                  (wcmatch(strcase ItemDescription)(strcase "*14/10/10*"))
                  (wcmatch(strcase ItemDescription)(strcase "*14/12/6*"))
                  (wcmatch(strcase ItemDescription)(strcase "*14/12/8*"))
                  (wcmatch(strcase ItemDescription)(strcase "*14/12/10*"))
                  (wcmatch(strcase ItemDescription)(strcase "*16/10/10*"))
                  (wcmatch(strcase ItemDescription)(strcase "*16/12/8*"))
                  (wcmatch(strcase ItemDescription)(strcase "*16/12/10*"))
                  (wcmatch(strcase ItemDescription)(strcase "*16/14/8*"))
                  (wcmatch(strcase ItemDescription)(strcase "*16/14/10*")))
               )
               (and
               (= ItemLengthAngle 20)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*14/12/12*"))
                  (wcmatch(strcase ItemDescription)(strcase "*16/12/12*"))
                  (wcmatch(strcase ItemDescription)(strcase "*16/14/12*")))
               )
               (and
               (= ItemLengthAngle 30)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*16/14/14*"))
                  (wcmatch(strcase ItemDescription)(strcase "*18/14/14*")))
               )
               (and
               (= ItemLengthAngle 18)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*6/6/6*"))
               (wcmatch(strcase ItemDescription)(strcase "*8/8/8*"))
               (wcmatch(strcase ItemDescription)(strcase "*10/10/6*"))
               (wcmatch(strcase ItemDescription)(strcase "*10/10/8*"))
               (wcmatch(strcase ItemDescription)(strcase "*10/10/10*"))
               (wcmatch(strcase ItemDescription)(strcase "*12/12/6*"))
               (wcmatch(strcase ItemDescription)(strcase "*12/12/8*"))
               (wcmatch(strcase ItemDescription)(strcase "*12/12/10*"))
               (wcmatch(strcase ItemDescription)(strcase "*14/14/6*"))
               (wcmatch(strcase ItemDescription)(strcase "*14/14/8*"))
               (wcmatch(strcase ItemDescription)(strcase "*14/14/10*"))
               (wcmatch(strcase ItemDescription)(strcase "*16/16/8*")))
               )
               (and
               (= ItemLengthAngle 20)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*12/12/12*"))
               (wcmatch(strcase ItemDescription)(strcase "*14/14/12*")))
               )
               (and
               (= ItemLengthAngle 30)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*14/14/14*")))
               )
               (and
               (wcmatch ItemCID "60")
               (wcmatch(strcase ItemSourceFileName)(strcase "*Cap*"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (wcmatch ItemCID "60")
               (wcmatch(strcase ItemSourceFileName)(strcase "*End Cap*"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (wcmatch ItemCID "1112")
               (wcmatch(strcase ItemDescription)(strcase "*3\" Collar*"))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*"))
                  (wcmatch(strcase ItemDescription)(strcase "*20\"*")))
               )
               (and
               (wcmatch ItemCID "1112")
               (wcmatch(strcase ItemDescription)(strcase "*Spin-in*"))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*")))
               )
               (and
                  (wcmatch(strcase ItemDescription)(strcase "*6\" Long Taper*"))
               (or(wcmatch(strcase ItemDescription)(strcase "*7-5*"))
                  (wcmatch(strcase ItemDescription)(strcase "*8-6*"))
                  (wcmatch(strcase ItemDescription)(strcase "*9-7*"))
                  (wcmatch(strcase ItemDescription)(strcase "*10-8*"))
                  (wcmatch(strcase ItemDescription)(strcase "*10-9*"))
                  (wcmatch(strcase ItemDescription)(strcase "*12-10*"))
                  (wcmatch(strcase ItemDescription)(strcase "*14-12*"))
                  (wcmatch(strcase ItemDescription)(strcase "*16-14*"))
                  (wcmatch(strcase ItemDescription)(strcase "*18-16*")))
               )
               (and
                  (wcmatch(strcase ItemDescription)(strcase "*12\" Long Taper*"))
               (or(wcmatch(strcase ItemDescription)(strcase "*10-6*"))
                  (wcmatch(strcase ItemDescription)(strcase "*12-8*"))
                  (wcmatch(strcase ItemDescription)(strcase "*14-10*"))
                  (wcmatch(strcase ItemDescription)(strcase "*16-12*"))
                  (wcmatch(strcase ItemDescription)(strcase "*18-14*"))
                  (wcmatch(strcase ItemDescription)(strcase "*8-5*"))
                  (wcmatch(strcase ItemDescription)(strcase "*7-6*"))
                  (wcmatch(strcase ItemDescription)(strcase "*9-6*"))
                  (wcmatch(strcase ItemDescription)(strcase "*8-7*"))
                  (wcmatch(strcase ItemDescription)(strcase "*9-7*"))
                  (wcmatch(strcase ItemDescription)(strcase "*10-7*"))
                  (wcmatch(strcase ItemDescription)(strcase "*12-7*"))
                  (wcmatch(strcase ItemDescription)(strcase "*10-9*"))
                  (wcmatch(strcase ItemDescription)(strcase "*12-6*"))
                  (wcmatch(strcase ItemDescription)(strcase "*12-10*"))
                  (wcmatch(strcase ItemDescription)(strcase "*18-10*")))
               )
               (and
                  (wcmatch(strcase ItemDescription)(strcase "*18\" Long Taper*"))
               (or(wcmatch(strcase ItemDescription)(strcase "*12-6*"))
                  (wcmatch(strcase ItemDescription)(strcase "*14-6*"))
                  (wcmatch(strcase ItemDescription)(strcase "*12-8*"))
                  (wcmatch(strcase ItemDescription)(strcase "*14-8*"))
                  (wcmatch(strcase ItemDescription)(strcase "*16-8*"))
                  (wcmatch(strcase ItemDescription)(strcase "*16-12*"))
                  (wcmatch(strcase ItemDescription)(strcase "*18-12*"))
                  (wcmatch(strcase ItemDescription)(strcase "*16-14*"))
                  (wcmatch(strcase ItemDescription)(strcase "*18-14*"))
                  (wcmatch(strcase ItemDescription)(strcase "*20-14*"))
                  (wcmatch(strcase ItemDescription)(strcase "*18-16*"))
                  (wcmatch(strcase ItemDescription)(strcase "*20-18*"))
                  (wcmatch(strcase ItemDescription)(strcase "*6-5*"))
                  (wcmatch(strcase ItemDescription)(strcase "*7-6*"))
                  (wcmatch(strcase ItemDescription)(strcase "*8-7*"))
                  (wcmatch(strcase ItemDescription)(strcase "*9-8*"))
                  (wcmatch(strcase ItemDescription)(strcase "*10-9*"))
                  (wcmatch(strcase ItemDescription)(strcase "*9-6*"))
                  (wcmatch(strcase ItemDescription)(strcase "*9-7*"))
                  (wcmatch(strcase ItemDescription)(strcase "*10-7*"))
                  (wcmatch(strcase ItemDescription)(strcase "*12-7*"))
                  (wcmatch(strcase ItemDescription)(strcase "*14-7*"))
                  (wcmatch(strcase ItemDescription)(strcase "*12-9*"))
                  (wcmatch(strcase ItemDescription)(strcase "*14-9*")))
               )
               (and
               (or(wcmatch(strcase ItemSourceFileName)(strcase "*45Deg on Rd Saddle*"))
                  (wcmatch(strcase ItemDescription)(strcase "*45 Deg Sad*"))
                  (wcmatch ItemCID "875"))
               (or(wcmatch(strcase ItemDescription)(strcase "*6\" on 6\"*"))
                  (wcmatch(strcase ItemDescription)(strcase "*6 on 6*"))
                  (wcmatch(strcase ItemDescription)(strcase "*6\" on 8\"*"))
                  (wcmatch(strcase ItemDescription)(strcase "*6 on 8*"))
                  (wcmatch(strcase ItemDescription)(strcase "*6\" on 10\"*"))
                  (wcmatch(strcase ItemDescription)(strcase "*6 on 10*"))
                  (wcmatch(strcase ItemDescription)(strcase "*6\" on 12\"*"))
                  (wcmatch(strcase ItemDescription)(strcase "*6 on 12*"))
                  (wcmatch(strcase ItemDescription)(strcase "*6\" on 14\"*"))
                  (wcmatch(strcase ItemDescription)(strcase "*6 on 14*"))
                  (wcmatch(strcase ItemDescription)(strcase "*6\" on 16\"*"))
                  (wcmatch(strcase ItemDescription)(strcase "*6 on 16*"))
                  (wcmatch(strcase ItemDescription)(strcase "*6\" on 18\"*"))
                  (wcmatch(strcase ItemDescription)(strcase "*6 on 18*"))
                  (wcmatch(strcase ItemDescription)(strcase "*8\" on 8\"*"))
                  (wcmatch(strcase ItemDescription)(strcase "*8 on 8*"))
                  (wcmatch(strcase ItemDescription)(strcase "*8\" on 10\"*"))
                  (wcmatch(strcase ItemDescription)(strcase "*8 on 10*"))
                  (wcmatch(strcase ItemDescription)(strcase "*8\" on 12\"*"))
                  (wcmatch(strcase ItemDescription)(strcase "*8 on 12*"))
                  (wcmatch(strcase ItemDescription)(strcase "*8\" on 14\"*"))
                  (wcmatch(strcase ItemDescription)(strcase "*8 on 14*"))
                  (wcmatch(strcase ItemDescription)(strcase "*8\" on 16\"*"))
                  (wcmatch(strcase ItemDescription)(strcase "*8 on 16*"))
                  (wcmatch(strcase ItemDescription)(strcase "*8\" on 18\"*"))
                  (wcmatch(strcase ItemDescription)(strcase "*8 on 18*"))
                  (wcmatch(strcase ItemDescription)(strcase "*10\" on 10\"*"))
                  (wcmatch(strcase ItemDescription)(strcase "*10 on 10*"))
                  (wcmatch(strcase ItemDescription)(strcase "*10\" on 12\"*"))
                  (wcmatch(strcase ItemDescription)(strcase "*10 on 12*"))
                  (wcmatch(strcase ItemDescription)(strcase "*10\" on 14\"*"))
                  (wcmatch(strcase ItemDescription)(strcase "*10 on 14*"))
                  (wcmatch(strcase ItemDescription)(strcase "*10\" on 16\"*"))
                  (wcmatch(strcase ItemDescription)(strcase "*10 on 16*"))
                  (wcmatch(strcase ItemDescription)(strcase "*10\" on 18\"*"))
                  (wcmatch(strcase ItemDescription)(strcase "*10 on 18*"))
                  (wcmatch(strcase ItemDescription)(strcase "*10\" on 20\"*"))
                  (wcmatch(strcase ItemDescription)(strcase "*10 on 20*"))
                  (wcmatch(strcase ItemDescription)(strcase "*14\" on 14\"*"))
                  (wcmatch(strcase ItemDescription)(strcase "*14 on 14*"))
                  (wcmatch(strcase ItemDescription)(strcase "*14\" on 16\"*"))
                  (wcmatch(strcase ItemDescription)(strcase "*14 on 16*")))
               )
               (and
               (or(wcmatch(strcase ItemSourceFileName)(strcase "*45Deg Flat Saddle*"))
                  (wcmatch(strcase ItemDescription)(strcase "*45D Flat*"))
                  (wcmatch ItemCID "16"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*")))
               )
               (and
               (or(wcmatch(strcase ItemSourceFileName)(strcase "*Rd on Rd Conical*"))
                  (wcmatch(strcase ItemDescription)(strcase "*#8 *"))
                  (wcmatch ItemCID "751"))
               (or(wcmatch(strcase ItemDescription)(strcase "*6\" on 8\"*"))
                  (wcmatch(strcase ItemDescription)(strcase "*6 on 8*"))
                  (wcmatch(strcase ItemDescription)(strcase "*6\" on 10\"*"))
                  (wcmatch(strcase ItemDescription)(strcase "*6 on 10*"))
                  (wcmatch(strcase ItemDescription)(strcase "*6\" on 12\"*"))
                  (wcmatch(strcase ItemDescription)(strcase "*6 on 12*"))
                  (wcmatch(strcase ItemDescription)(strcase "*6\" on 14\"*"))
                  (wcmatch(strcase ItemDescription)(strcase "*6 on 14*"))
                  (wcmatch(strcase ItemDescription)(strcase "*6\" on 16\"*"))
                  (wcmatch(strcase ItemDescription)(strcase "*6 on 16*"))
                  (wcmatch(strcase ItemDescription)(strcase "*6\" on 18\"*"))
                  (wcmatch(strcase ItemDescription)(strcase "*6 on 18*"))
                  (wcmatch(strcase ItemDescription)(strcase "*6\" on 20\"*"))
                  (wcmatch(strcase ItemDescription)(strcase "*6 on 20*"))
                  (wcmatch(strcase ItemDescription)(strcase "*8\" on 10\"*"))
                  (wcmatch(strcase ItemDescription)(strcase "*8 on 10*"))
                  (wcmatch(strcase ItemDescription)(strcase "*8\" on 12\"*"))
                  (wcmatch(strcase ItemDescription)(strcase "*8 on 12*"))
                  (wcmatch(strcase ItemDescription)(strcase "*8\" on 14\"*"))
                  (wcmatch(strcase ItemDescription)(strcase "*8 on 14*"))
                  (wcmatch(strcase ItemDescription)(strcase "*8\" on 16\"*"))
                  (wcmatch(strcase ItemDescription)(strcase "*8 on 16*"))
                  (wcmatch(strcase ItemDescription)(strcase "*8\" on 18\"*"))
                  (wcmatch(strcase ItemDescription)(strcase "*8 on 18*"))
                  (wcmatch(strcase ItemDescription)(strcase "*10\" on 12\"*"))
                  (wcmatch(strcase ItemDescription)(strcase "*10 on 12*"))
                  (wcmatch(strcase ItemDescription)(strcase "*10\" on 14\"*"))
                  (wcmatch(strcase ItemDescription)(strcase "*10 on 14*"))
                  (wcmatch(strcase ItemDescription)(strcase "*10\" on 16\"*"))
                  (wcmatch(strcase ItemDescription)(strcase "*10 on 16*"))
                  (wcmatch(strcase ItemDescription)(strcase "*10\" on 18\"*"))
                  (wcmatch(strcase ItemDescription)(strcase "*10 on 18*"))
                  (wcmatch(strcase ItemDescription)(strcase "*12\" on 14\"*"))
                  (wcmatch(strcase ItemDescription)(strcase "*12 on 14*"))
                  (wcmatch(strcase ItemDescription)(strcase "*12\" on 16\"*"))
                  (wcmatch(strcase ItemDescription)(strcase "*12 on 16*"))
                  (wcmatch(strcase ItemDescription)(strcase "*12\" on 18\"*"))
                  (wcmatch(strcase ItemDescription)(strcase "*12 on 18*"))
                  (wcmatch(strcase ItemDescription)(strcase "*12\" on 20\"*"))
                  (wcmatch(strcase ItemDescription)(strcase "*12 on 20*"))
                  (wcmatch(strcase ItemDescription)(strcase "*14\" on 16\"*"))
                  (wcmatch(strcase ItemDescription)(strcase "*14 on 16*"))
                  (wcmatch(strcase ItemDescription)(strcase "*14\" on 18\"*"))
                  (wcmatch(strcase ItemDescription)(strcase "*14 on 18*")))
               )
               (and
               (or(wcmatch(strcase ItemSourceFileName)(strcase "*Round Access Door*"))
                  (wcmatch(strcase ItemSourceFileName)(strcase "*#7 Access Door*")))
               (or(wcmatch(strcase ItemDescription)(strcase "*6\"*"))
                  (wcmatch(strcase ItemDescription)(strcase "*8\"*"))
                  (wcmatch(strcase ItemDescription)(strcase "*10\"*"))
                  (wcmatch(strcase ItemDescription)(strcase "*12\"*"))
                  (wcmatch(strcase ItemDescription)(strcase "*14\"*")))
               )
               (and
               (or(wcmatch(strcase ItemSourceFileName)(strcase "*Conical Flat Tap*"))
                  (wcmatch(strcase ItemSourceFileName)(strcase "*Flat Conical 1\" Flg*"))
                  (wcmatch ItemCID "345"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(and(wcmatch ItemCID "51")(wcmatch(strcase ItemSourceFileName)(strcase "*6\" Start Collar wFlg*"))(wcmatch(strcase ItemDescription)(strcase "*for Damper*")))
                  (and(wcmatch ItemCID "51")(wcmatch(strcase ItemDescription)(strcase "*Damper*"))))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(and(wcmatch ItemCID "51")(wcmatch(strcase ItemSourceFileName)(strcase "*6\" Start Collar wFlg*"))(not(wcmatch(strcase ItemDescription)(strcase "*for Damper*"))))
                  (and(wcmatch ItemCID "51")(not(wcmatch(strcase ItemDescription)(strcase "*Damper*")))))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*")))
               )
               (and
               (or(wcmatch(strcase ItemSourceFileName)(strcase "Coupling")))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(wcmatch ItemCID "522")
                  (wcmatch(strcase ItemSourceFileName)(strcase "#2 Coupling")))
               (or(= dim1 6)
                  (= dim1 7)
                  (= dim1 8)
                  (= dim1 9)
                  (= dim1 10)
                  (= dim1 12)
                  (= dim1 14)
                  (= dim1 16)
                  (= dim1 18)
                  (= dim1 20))
               )
               )
               )
              (setq Activity# "316")
              (if(or
                 (or(wcmatch(strcase ItemSourceFileName)(strcase "*Conical Cross*"))
                    (wcmatch(strcase ItemSourceFileName)(strcase "*Conical Tee*"))
                    (wcmatch(strcase ItemSourceFileName)(strcase "*90 Adj.*"))
                    (wcmatch(strcase ItemSourceFileName)(strcase "*45 Adj.*"))
                    (wcmatch(strcase ItemSourceFileName)(strcase "*Misc. Elbow*"))
                    (wcmatch(strcase ItemSourceFileName)(strcase "*Welded Elbow*"))
                    (wcmatch(strcase ItemSourceFileName)(strcase "*90Deg Adj.*"))
                    (wcmatch(strcase ItemSourceFileName)(strcase "*45Deg Adj.*"))
                    (wcmatch(strcase ItemSourceFileName)(strcase "Misc. Adj. Elbow*"))
                    (wcmatch(strcase ItemSourceFileName)(strcase "Misc. Adjustable Elbow*"))
                    (wcmatch(strcase ItemSourceFileName)(strcase "Misc. El*"))
                    (wcmatch(strcase ItemSourceFileName)(strcase "*Shoe Barrel*"))
                    (wcmatch(strcase ItemSourceFileName)(strcase "*Shoe Saddle*"))
                    (wcmatch(strcase ItemSourceFileName)(strcase "*Mitered Offset Fixed*"))
                    (wcmatch(strcase ItemSourceFileName)(strcase "*Deflector Hood*"))
                    (wcmatch(strcase ItemSourceFileName)(strcase "*FULL RAD.*"))
                    (wcmatch(strcase ItemSourceFileName)(strcase "*HALF RAD.*"))
                    (wcmatch(strcase ItemSourceFileName)(strcase "*Pancake*"))
                    (wcmatch(strcase ItemSourceFileName)(strcase "*Flex*"))
                    (wcmatch(strcase ItemSourceFileName)(strcase "*Welded Pipe*"))
                    (wcmatch(strcase ItemDescription)(strcase "* CROSS*"))
                 )
                 (and
                 (= ItemLengthAngle 18)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*8/6/6*"))
                    (wcmatch(strcase ItemDescription)(strcase "*10/8/6*"))
                    (wcmatch(strcase ItemDescription)(strcase "*10/8/8*"))
                    (wcmatch(strcase ItemDescription)(strcase "*12/8/6*"))
                    (wcmatch(strcase ItemDescription)(strcase "*12/8/8*"))
                    (wcmatch(strcase ItemDescription)(strcase "*12/10/6*"))
                    (wcmatch(strcase ItemDescription)(strcase "*12/10/8*"))
                    (wcmatch(strcase ItemDescription)(strcase "*12/10/10*"))
                    (wcmatch(strcase ItemDescription)(strcase "*14/10/8*"))
                    (wcmatch(strcase ItemDescription)(strcase "*14/10/10*"))
                    (wcmatch(strcase ItemDescription)(strcase "*14/12/6*"))
                    (wcmatch(strcase ItemDescription)(strcase "*14/12/8*"))
                    (wcmatch(strcase ItemDescription)(strcase "*14/12/10*"))
                    (wcmatch(strcase ItemDescription)(strcase "*16/10/10*"))
                    (wcmatch(strcase ItemDescription)(strcase "*16/12/8*"))
                    (wcmatch(strcase ItemDescription)(strcase "*16/12/10*"))
                    (wcmatch(strcase ItemDescription)(strcase "*16/14/8*"))
                    (wcmatch(strcase ItemDescription)(strcase "*16/14/10*"))))
                 )
                 (and
                 (= ItemLengthAngle 20)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*14/12/12*"))
                    (wcmatch(strcase ItemDescription)(strcase "*16/12/12*"))
                    (wcmatch(strcase ItemDescription)(strcase "*16/14/12*"))))
                 )
                 (and
                 (= ItemLengthAngle 30)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*16/14/14*"))
                    (wcmatch(strcase ItemDescription)(strcase "*18/14/14*"))))
                 )
                 (and
                 (= ItemLengthAngle 18)
                 (or(wcmatch(strcase ItemSourceFileName)(strcase "*Lateral 45*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*6/6/6*"))
                 (wcmatch(strcase ItemDescription)(strcase "*8/8/8*"))
                 (wcmatch(strcase ItemDescription)(strcase "*10/10/6*"))
                 (wcmatch(strcase ItemDescription)(strcase "*10/10/8*"))
                 (wcmatch(strcase ItemDescription)(strcase "*10/10/10*"))
                 (wcmatch(strcase ItemDescription)(strcase "*12/12/6*"))
                 (wcmatch(strcase ItemDescription)(strcase "*12/12/8*"))
                 (wcmatch(strcase ItemDescription)(strcase "*12/12/10*"))
                 (wcmatch(strcase ItemDescription)(strcase "*14/14/6*"))
                 (wcmatch(strcase ItemDescription)(strcase "*14/14/8*"))
                 (wcmatch(strcase ItemDescription)(strcase "*14/14/10*"))
                 (wcmatch(strcase ItemDescription)(strcase "*16/16/8*"))))
                 )
                 (and
                 (= ItemLengthAngle 20)
                 (or(wcmatch(strcase ItemSourceFileName)(strcase "*Lateral 45*"))
                 (wcmatch(strcase ItemSourceFileName)(strcase "*No Dampers*"))
                 (wcmatch(strcase ItemSourceFileName)(strcase "*KS7L*"))
                 (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*12/12/12*"))
                 (wcmatch(strcase ItemDescription)(strcase "*14/14/12*"))))
                 )
                 (and
                 (= ItemLengthAngle 30)
                 (or(wcmatch(strcase ItemSourceFileName)(strcase "*Lateral 45*"))
                 (wcmatch(strcase ItemSourceFileName)(strcase "*No Dampers*"))
                 (wcmatch(strcase ItemSourceFileName)(strcase "*KS7L*"))
                 (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*14/14/14*"))))
                 )
                 (and(wcmatch ItemCID "60")
                     (wcmatch(strcase ItemSourceFileName)(strcase "*Cap*"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and(wcmatch ItemCID "60")
                     (wcmatch(strcase ItemSourceFileName)(strcase "*End Cap*"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and(wcmatch ItemCID "1112")
                     (wcmatch(strcase ItemDescription)(strcase "*3\" Collar*"))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))
                    (wcmatch(strcase ItemDescription)(strcase "*20\"*"))))
                 )
                 (and(wcmatch ItemCID "1112")
                     (wcmatch(strcase ItemDescription)(strcase "*Spin-in*"))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))))
                 )
                 (and(wcmatch(strcase ItemDescription)(strcase "*6\" Long Taper*"))
                 (not(or(wcmatch(strcase ItemDescription)(strcase "*7-5*"))
                    (wcmatch(strcase ItemDescription)(strcase "*8-6*"))
                    (wcmatch(strcase ItemDescription)(strcase "*9-7*"))
                    (wcmatch(strcase ItemDescription)(strcase "*10-8*"))
                    (wcmatch(strcase ItemDescription)(strcase "*10-9*"))
                    (wcmatch(strcase ItemDescription)(strcase "*12-10*"))
                    (wcmatch(strcase ItemDescription)(strcase "*14-12*"))
                    (wcmatch(strcase ItemDescription)(strcase "*16-14*"))
                    (wcmatch(strcase ItemDescription)(strcase "*18-16*"))))
                 )
                 (and(wcmatch(strcase ItemDescription)(strcase "*12\" Long Taper*"))
                 (not(or(wcmatch(strcase ItemDescription)(strcase "*10-6*"))
                    (wcmatch(strcase ItemDescription)(strcase "*12-8*"))
                    (wcmatch(strcase ItemDescription)(strcase "*14-10*"))
                    (wcmatch(strcase ItemDescription)(strcase "*16-12*"))
                    (wcmatch(strcase ItemDescription)(strcase "*18-14*"))
                    (wcmatch(strcase ItemDescription)(strcase "*8-5*"))
                    (wcmatch(strcase ItemDescription)(strcase "*7-6*"))
                    (wcmatch(strcase ItemDescription)(strcase "*9-6*"))
                    (wcmatch(strcase ItemDescription)(strcase "*8-7*"))
                    (wcmatch(strcase ItemDescription)(strcase "*9-7*"))
                    (wcmatch(strcase ItemDescription)(strcase "*10-7*"))
                    (wcmatch(strcase ItemDescription)(strcase "*12-7*"))
                    (wcmatch(strcase ItemDescription)(strcase "*10-9*"))
                    (wcmatch(strcase ItemDescription)(strcase "*12-6*"))
                    (wcmatch(strcase ItemDescription)(strcase "*12-10*"))
                    (wcmatch(strcase ItemDescription)(strcase "*18-10*"))))
                 )
                 (and(wcmatch(strcase ItemDescription)(strcase "*18\" Long Taper*"))
                 (not(or(wcmatch(strcase ItemDescription)(strcase "*12-6*"))
                    (wcmatch(strcase ItemDescription)(strcase "*14-6*"))
                    (wcmatch(strcase ItemDescription)(strcase "*12-8*"))
                    (wcmatch(strcase ItemDescription)(strcase "*14-8*"))
                    (wcmatch(strcase ItemDescription)(strcase "*16-8*"))
                    (wcmatch(strcase ItemDescription)(strcase "*16-12*"))
                    (wcmatch(strcase ItemDescription)(strcase "*18-12*"))
                    (wcmatch(strcase ItemDescription)(strcase "*16-14*"))
                    (wcmatch(strcase ItemDescription)(strcase "*18-14*"))
                    (wcmatch(strcase ItemDescription)(strcase "*20-14*"))
                    (wcmatch(strcase ItemDescription)(strcase "*18-16*"))
                    (wcmatch(strcase ItemDescription)(strcase "*20-18*"))
                    (wcmatch(strcase ItemDescription)(strcase "*6-5*"))
                    (wcmatch(strcase ItemDescription)(strcase "*7-6*"))
                    (wcmatch(strcase ItemDescription)(strcase "*8-7*"))
                    (wcmatch(strcase ItemDescription)(strcase "*9-8*"))
                    (wcmatch(strcase ItemDescription)(strcase "*10-9*"))
                    (wcmatch(strcase ItemDescription)(strcase "*9-6*"))
                    (wcmatch(strcase ItemDescription)(strcase "*9-7*"))
                    (wcmatch(strcase ItemDescription)(strcase "*10-7*"))
                    (wcmatch(strcase ItemDescription)(strcase "*12-7*"))
                    (wcmatch(strcase ItemDescription)(strcase "*14-7*"))
                    (wcmatch(strcase ItemDescription)(strcase "*12-9*"))
                    (wcmatch(strcase ItemDescription)(strcase "*14-9*"))))
                 )
                 (and
                 (or(wcmatch(strcase ItemSourceFileName)(strcase "*45Deg on Rd Saddle*"))
                    (wcmatch(strcase ItemDescription)(strcase "*45 Deg Sad*"))
                    (wcmatch ItemCID "875"))
                 (not(or(wcmatch(strcase ItemDescription)(strcase "*6\" on 6\"*"))
                    (wcmatch(strcase ItemDescription)(strcase "*6 on 6*"))
                    (wcmatch(strcase ItemDescription)(strcase "*6\" on 8\"*"))
                    (wcmatch(strcase ItemDescription)(strcase "*6 on 8*"))
                    (wcmatch(strcase ItemDescription)(strcase "*6\" on 10\"*"))
                    (wcmatch(strcase ItemDescription)(strcase "*6 on 10*"))
                    (wcmatch(strcase ItemDescription)(strcase "*6\" on 12\"*"))
                    (wcmatch(strcase ItemDescription)(strcase "*6 on 12*"))
                    (wcmatch(strcase ItemDescription)(strcase "*6\" on 14\"*"))
                    (wcmatch(strcase ItemDescription)(strcase "*6 on 14*"))
                    (wcmatch(strcase ItemDescription)(strcase "*6\" on 16\"*"))
                    (wcmatch(strcase ItemDescription)(strcase "*6 on 16*"))
                    (wcmatch(strcase ItemDescription)(strcase "*6\" on 18\"*"))
                    (wcmatch(strcase ItemDescription)(strcase "*6 on 18*"))
                    (wcmatch(strcase ItemDescription)(strcase "*8\" on 8\"*"))
                    (wcmatch(strcase ItemDescription)(strcase "*8 on 8*"))
                    (wcmatch(strcase ItemDescription)(strcase "*8\" on 10\"*"))
                    (wcmatch(strcase ItemDescription)(strcase "*8 on 10*"))
                    (wcmatch(strcase ItemDescription)(strcase "*8\" on 12\"*"))
                    (wcmatch(strcase ItemDescription)(strcase "*8 on 12*"))
                    (wcmatch(strcase ItemDescription)(strcase "*8\" on 14\"*"))
                    (wcmatch(strcase ItemDescription)(strcase "*8 on 14*"))
                    (wcmatch(strcase ItemDescription)(strcase "*8\" on 16\"*"))
                    (wcmatch(strcase ItemDescription)(strcase "*8 on 16*"))
                    (wcmatch(strcase ItemDescription)(strcase "*8\" on 18\"*"))
                    (wcmatch(strcase ItemDescription)(strcase "*8 on 18*"))
                    (wcmatch(strcase ItemDescription)(strcase "*10\" on 10\"*"))
                    (wcmatch(strcase ItemDescription)(strcase "*10 on 10*"))
                    (wcmatch(strcase ItemDescription)(strcase "*10\" on 12\"*"))
                    (wcmatch(strcase ItemDescription)(strcase "*10 on 12*"))
                    (wcmatch(strcase ItemDescription)(strcase "*10\" on 14\"*"))
                    (wcmatch(strcase ItemDescription)(strcase "*10 on 14*"))
                    (wcmatch(strcase ItemDescription)(strcase "*10\" on 16\"*"))
                    (wcmatch(strcase ItemDescription)(strcase "*10 on 16*"))
                    (wcmatch(strcase ItemDescription)(strcase "*10\" on 18\"*"))
                    (wcmatch(strcase ItemDescription)(strcase "*10 on 18*"))
                    (wcmatch(strcase ItemDescription)(strcase "*10\" on 20\"*"))
                    (wcmatch(strcase ItemDescription)(strcase "*10 on 20*"))
                    (wcmatch(strcase ItemDescription)(strcase "*14\" on 14\"*"))
                    (wcmatch(strcase ItemDescription)(strcase "*14 on 14*"))
                    (wcmatch(strcase ItemDescription)(strcase "*14\" on 16\"*"))
                    (wcmatch(strcase ItemDescription)(strcase "*14 on 16*"))))
                 )
                 (and
                 (or(wcmatch(strcase ItemSourceFileName)(strcase "*45Deg Flat Saddle*"))
                    (wcmatch(strcase ItemDescription)(strcase "*45D Flat*"))
                    (wcmatch ItemCID "16"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))))
                 )
                 (and
                 (or(wcmatch(strcase ItemSourceFileName)(strcase "*Rd on Rd Conical*"))
                    (wcmatch(strcase ItemDescription)(strcase "*#8 *"))
                    (wcmatch ItemCID "751"))
                 (not(or(wcmatch(strcase ItemDescription)(strcase "*6\" on 8\"*"))
                    (wcmatch(strcase ItemDescription)(strcase "*6 on 8*"))
                    (wcmatch(strcase ItemDescription)(strcase "*6\" on 10\"*"))
                    (wcmatch(strcase ItemDescription)(strcase "*6 on 10*"))
                    (wcmatch(strcase ItemDescription)(strcase "*6\" on 12\"*"))
                    (wcmatch(strcase ItemDescription)(strcase "*6 on 12*"))
                    (wcmatch(strcase ItemDescription)(strcase "*6\" on 14\"*"))
                    (wcmatch(strcase ItemDescription)(strcase "*6 on 14*"))
                    (wcmatch(strcase ItemDescription)(strcase "*6\" on 16\"*"))
                    (wcmatch(strcase ItemDescription)(strcase "*6 on 16*"))
                    (wcmatch(strcase ItemDescription)(strcase "*6\" on 18\"*"))
                    (wcmatch(strcase ItemDescription)(strcase "*6 on 18*"))
                    (wcmatch(strcase ItemDescription)(strcase "*6\" on 20\"*"))
                    (wcmatch(strcase ItemDescription)(strcase "*6 on 20*"))
                    (wcmatch(strcase ItemDescription)(strcase "*8\" on 10\"*"))
                    (wcmatch(strcase ItemDescription)(strcase "*8 on 10*"))
                    (wcmatch(strcase ItemDescription)(strcase "*8\" on 12\"*"))
                    (wcmatch(strcase ItemDescription)(strcase "*8 on 12*"))
                    (wcmatch(strcase ItemDescription)(strcase "*8\" on 14\"*"))
                    (wcmatch(strcase ItemDescription)(strcase "*8 on 14*"))
                    (wcmatch(strcase ItemDescription)(strcase "*8\" on 16\"*"))
                    (wcmatch(strcase ItemDescription)(strcase "*8 on 16*"))
                    (wcmatch(strcase ItemDescription)(strcase "*8\" on 18\"*"))
                    (wcmatch(strcase ItemDescription)(strcase "*8 on 18*"))
                    (wcmatch(strcase ItemDescription)(strcase "*10\" on 12\"*"))
                    (wcmatch(strcase ItemDescription)(strcase "*10 on 12*"))
                    (wcmatch(strcase ItemDescription)(strcase "*10\" on 14\"*"))
                    (wcmatch(strcase ItemDescription)(strcase "*10 on 14*"))
                    (wcmatch(strcase ItemDescription)(strcase "*10\" on 16\"*"))
                    (wcmatch(strcase ItemDescription)(strcase "*10 on 16*"))
                    (wcmatch(strcase ItemDescription)(strcase "*10\" on 18\"*"))
                    (wcmatch(strcase ItemDescription)(strcase "*10 on 18*"))
                    (wcmatch(strcase ItemDescription)(strcase "*12\" on 14\"*"))
                    (wcmatch(strcase ItemDescription)(strcase "*12 on 14*"))
                    (wcmatch(strcase ItemDescription)(strcase "*12\" on 16\"*"))
                    (wcmatch(strcase ItemDescription)(strcase "*12 on 16*"))
                    (wcmatch(strcase ItemDescription)(strcase "*12\" on 18\"*"))
                    (wcmatch(strcase ItemDescription)(strcase "*12 on 18*"))
                    (wcmatch(strcase ItemDescription)(strcase "*12\" on 20\"*"))
                    (wcmatch(strcase ItemDescription)(strcase "*12 on 20*"))
                    (wcmatch(strcase ItemDescription)(strcase "*14\" on 16\"*"))
                    (wcmatch(strcase ItemDescription)(strcase "*14 on 16*"))
                    (wcmatch(strcase ItemDescription)(strcase "*14\" on 18\"*"))
                    (wcmatch(strcase ItemDescription)(strcase "*14 on 18*"))))
                 )
                 (and
                 (or(wcmatch(strcase ItemSourceFileName)(strcase "*Round Access Door*"))
                    (wcmatch(strcase ItemSourceFileName)(strcase "*#7 Access Door*")))
                 (not(or(wcmatch(strcase ItemDescription)(strcase "*6\"*"))
                    (wcmatch(strcase ItemDescription)(strcase "*8\"*"))
                    (wcmatch(strcase ItemDescription)(strcase "*10\"*"))
                    (wcmatch(strcase ItemDescription)(strcase "*12\"*"))
                    (wcmatch(strcase ItemDescription)(strcase "*14\"*"))))
                 )
                 (and
                 (or(wcmatch(strcase ItemSourceFileName)(strcase "*Conical Flat Tap*"))
                    (wcmatch(strcase ItemSourceFileName)(strcase "*Flat Conical 1\" Flg*"))
                    (wcmatch ItemCID "345"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(and(wcmatch ItemCID "51")(wcmatch(strcase ItemSourceFileName)(strcase "*6\" Start Collar wFlg*"))(wcmatch(strcase ItemDescription)(strcase "*for Damper*")))
                    (and(wcmatch ItemCID "51")(wcmatch(strcase ItemDescription)(strcase "*Damper*"))))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(and(wcmatch ItemCID "51")(wcmatch(strcase ItemSourceFileName)(strcase "*6\" Start Collar wFlg*"))(not(wcmatch(strcase ItemDescription)(strcase "*for Damper*"))))
                    (and(wcmatch ItemCID "51")(not(wcmatch(strcase ItemDescription)(strcase "*Damper*")))))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))))
                 )
                 (and
                 (or(wcmatch(strcase ItemSourceFileName)(strcase "Coupling")))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(wcmatch ItemCID "522")
                    (wcmatch(strcase ItemSourceFileName)(strcase "#2 Coupling")))
                 (not(or(= dim1 6)
                    (= dim1 7)
                    (= dim1 8)
                    (= dim1 9)
                    (= dim1 10)
                    (= dim1 12)
                    (= dim1 14)
                    (= dim1 16)
                    (= dim1 18)
                    (= dim1 20)))
                 )
                 )
                (setq Activity# "313")
                (if(and(not(or(wcmatch(strcase ItemService)(strcase "*Weld*"))(wcmatch(strcase ItemServiceType)(strcase "*Equipment*"))))
		  (or
                   (and(wcmatch(strcase ItemDescription)(strcase "Straight"))
                       (wcmatch(strcase c1Spec)(strcase "TDF"))
                       (/= ItemLengthAngle 56)
                   )
                   (and(wcmatch(strcase ItemDescription)(strcase "Straight"))
                       (or(wcmatch(strcase c1Spec)(strcase "Stand S&D"))
                          (wcmatch(strcase c1Spec)(strcase "Flat S&D")))
                       (/= ItemLengthAngle 59))
                   (wcmatch(strcase ItemDescription)(strcase "Cut Joint"))
                   (wcmatch(strcase ItemDescription)(strcase "Plenum"))
                   (wcmatch(strcase ItemSourceFileName)(strcase "Transition"))
                   (wcmatch(strcase ItemSourceFileName)(strcase "*Rect Elbow"))
                   (wcmatch(strcase ItemSourceFileName)(strcase "F16"))
                   (wcmatch(strcase ItemSourceFileName)(strcase "F 16"))
                   (wcmatch(strcase ItemSourceFileName)(strcase "F17"))
                   (wcmatch(strcase ItemSourceFileName)(strcase "F41"))
                   (wcmatch(strcase ItemSourceFileName)(strcase "F2"))
                   (wcmatch(strcase ItemSourceFileName)(strcase "F4"))
                   (wcmatch(strcase ItemSourceFileName)(strcase "SQ-RD"))
                   (wcmatch(strcase ItemSourceFileName)(strcase "TDF CAP"))
                   (wcmatch(strcase ItemSourceFileName)(strcase "SD CAP"))
                   (wcmatch(strcase ItemSourceFileName)(strcase "PLUG CAP"))
                   (wcmatch(strcase ItemSourceFileName)(strcase "S&D CAP"))
                   ))
                  (setq Activity# "317")
                (if(wcmatch(strcase ItemService)(strcase "*Weld*"))
                  (setq Activity# "318")
		  (setq Activity# "Unassigned")

		 ) ) ) ) ) ) ) ) ) ) );end ifs
      (vlax-put-property vla "CustomData" (strcat "ItemCID" " = " ItemCID ","))
      (vlax-put-property vla "CustomData" (strcat "Activity_#" " = " Activity# ","))
        (setq i (1+ i))
      );end while
  (princ "Thank you for waiting, this drawing and its items have been updated with Job information, Activity Numbers, and ItemCIDs")
    );end progn
  (princ "This drawing has been updated with Job information.")
  );end if
  (princ)
);end defun
;**************************************************************************************************************************************************
(defun c:Store_Sections ()
  (setq oldCurrentLayer (getvar "CLAYER"))
  (tblnext "layer" T)
  (while(setq evalLayer (cdr(assoc 2 (tblnext "layer"))))
    (if(wcmatch evalLayer "*FLOR-SECT-HGHT*")
      (setq existingSectionLayerList (append existingSectionLayerList (list evalLayer)))
    );end if
  );end while
  (setq i 0
        sset (ssget "_X" '((0 . "MAPS_SOLID")(-4 . "<OR")(300 . "STRAIGHT")(300 . "*SPIRAL")(-4 . "OR>"))));end setq
  (OUTSIDE_LOOP_VARIABLES sset)
  (while(< i limit)
    (INSIDE_LOOP_VARIABLES sset i)
    (setq makeThisLayer T)
    (if(not(= hitlist nil))
      (foreach elmt hitlist
        (if(wcmatch elmt ItemSectionName)
          (setq makeThisLayer nil)
        );end if
      );end foreach
    );end if
    (if(not(= existingSectionLayerList nil))
      (foreach elmt existingSectionLayerList
        (if(wcmatch elmt (strcat "*" (vl-string-subst "-" ": " ItemSectionName) "*"))
          (setq makeThisLayer nil)
        );end if
      );end foreach
    );end if
    (if(and makeThisLayer (not slopedItem)(not(wcmatch ItemSectionName "None")))
      (progn
        (command ".copy" ent "" (list c1x c1y c1z) (list c1x c1y 0))
        (setq itemCopy (ssadd (entlast))
              hitlist (append hitlist (list ItemSectionName)))
        (settext itemCopy 4 "on")
        (command "explode" itemCopy)
        (setq debris (ssget "_P")
              floorSection (+ (/ c1depth 2)(FORCE_POSITIVE (distof(cdr(assoc 1 (entget(entnext(ssname(ssget "P" '((2 . "ELEV")))0)))))))))
        (command "erase" debris "")
        (setq ItemSectionLayerName (strcat "M-AMC-FLOR-SECT-HGHT-(" (vl-string-subst "-" ": " ItemSectionName) ")-[" (rtos floorSection 2 0) "]"))
        (command "_.layer" "_make" ItemSectionLayerName "lock" ItemSectionLayerName "")
      );end progn
    );end if
    (setq i (1+ i))
  );end while
  (setvar "CLAYER" oldCurrentLayer)
  (setq evalLayer nil
        existingSectionLayerList nil
        i nil
        sset nil
        makeThisLayer nil
        hitlist nil
        itemCopy nil
        debris nil
        floorSection nil
        ItemSectionLayerName nil)
  (princ)
);end defun
;**************************************************************************************************************************************************
(defun c:Update_Drawing ()
  (setvar "cmdecho" 0)
  (OUTSIDE_LOOP_VARIABLES nil)
  (terpri)(princ "Updating Blocks --")(princ)
  (if(not(= block_WorkingTemplateName nil))(command "._purge" "B" block_WorkingTemplateName "Y" (if(> (getvar 'cmdactive) 0) "Y")))
  (if(not(= block_WorkingTemplateName nil))(command "._insert" (strcat customBlocksDirectory "\\" block_WorkingTemplateName)(command)))
  (if(not(= block_ElevName nil))(command "._insert" (strcat customBlocksDirectory "\\" block_SizeName)(command))(command "attsync" "n" block_ElevName))
  (if(not(= block_SizeName nil))(command "._insert" (strcat customBlocksDirectory "\\" block_SizeName)(command))(command "attsync" "n" block_SizeName))
  (if(not(= block_DiamName nil))(command "._insert" (strcat customBlocksDirectory "\\" block_DiamName)(command))(command "attsync" "n" block_DiamName))
  (if(not(= block_TagName nil))(command "._insert" (strcat customBlocksDirectory "\\" block_TagName)(command))(command "attsync" "n" block_TagName))
  (if(not(= block_StampName nil))(command "._insert" (strcat customBlocksDirectory "\\" block_StampName)(command))(command "attsync" "n" block_StampName))
  (if(not(= block_TitleBlockName nil))(command "._insert" (strcat customBlocksDirectory "\\" block_TitleBlockName)(command))(command "attsync" "n" block_TitleBlockName))
  (Delete_TextDummy_Layer&Items)
  (c:Set_Layer_Filters)
  (terpri)(princ "-- Blocks Updated")(princ)
  (setq i 0
        sset (ssget "X" '((0 . "MAPS_SOLID"))));end setq
  (if(not(= sset nil))
    (progn
      (terpri)(princ "Updating Services and Specifications --")(princ)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if ((wildcard(item.service, \"*SUPPLY*\") = 1) and (wildcard(item.service, \"*2\"+qt+\"*\") = 1)) or ((wildcard(item.specification, \"*+2*\") = 1) and (wildcard(item.service, \"*None*\") = 1)) then" writeToVBCode)
(write-line "item.service = \"Supply Air (+2''WG) Low Pressure\"" writeToVBCode)
(write-line "item.update()" writeToVBCode)
(write-line "elseif ((wildcard(item.service, \"*SUPPLY*\") = 1) and (wildcard(item.service, \"*3\"+qt+\"*\") = 1)) or ((wildcard(item.specification, \"*+3*\") = 1) and (wildcard(item.service, \"*None*\") = 1)) then" writeToVBCode)
(write-line "item.service = \"Supply Air (+3''WG) Medium Pressure\"" writeToVBCode)
(write-line "item.update()" writeToVBCode)
(write-line "elseif ((wildcard(item.service, \"*SUPPLY*\") = 1) and (wildcard(item.service, \"*4\"+qt+\"*\") = 1)) or ((wildcard(item.specification, \"*+4*\") = 1) and (wildcard(item.service, \"*None*\") = 1)) then" writeToVBCode)
(write-line "item.service = \"Supply Air (+4''WG) High Pressure\"" writeToVBCode)
(write-line "item.update()" writeToVBCode)
(write-line "elseif ((wildcard(item.service, \"*SUPPLY*\") = 1) and (wildcard(item.service, \"*6\"+qt+\"*\") = 1)) or ((wildcard(item.specification, \"*+6*\") = 1) and (wildcard(item.service, \"*None*\") = 1)) then" writeToVBCode)
(write-line "item.service = \"Supply Air (+6''WG) High Pressure\"" writeToVBCode)
(write-line "item.update()" writeToVBCode)
(write-line "elseif ((wildcard(item.service, \"*SUPPLY*\") = 1) and (wildcard(item.service, \"*10\"+qt+\"*\") = 1)) or ((wildcard(item.specification, \"*+10*\") = 1) and (wildcard(item.service, \"*None*\") = 1)) then" writeToVBCode)
(write-line "item.service = \"Supply Air (+10''WG) High Pressure\"" writeToVBCode)
(write-line "item.update()" writeToVBCode)
(write-line "elseif ((wildcard(item.service, \"*RETURN*\") = 1) and (wildcard(item.service, \"*2\"+qt+\"*\") = 1)) then" writeToVBCode)
(write-line "item.service = \"Return Air (-2''WG) Low Pressure\"" writeToVBCode)
(write-line "item.update()" writeToVBCode)
(write-line "elseif ((wildcard(item.service, \"*RETURN*\") = 1) and (wildcard(item.service, \"*3\"+qt+\"*\") = 1)) then" writeToVBCode)
(write-line "item.service = \"Return Air (-3''WG) Medium Pressure\"" writeToVBCode)
(write-line "item.update()" writeToVBCode)
(write-line "elseif ((wildcard(item.service, \"*RETURN*\") = 1) and (wildcard(item.service, \"*4\"+qt+\"*\") = 1)) then" writeToVBCode)
(write-line "item.service = \"Return Air (-4''WG) High Pressure\"" writeToVBCode)
(write-line "item.update()" writeToVBCode)
(write-line "elseif ((wildcard(item.service, \"*RETURN*\") = 1) and (wildcard(item.service, \"*6\"+qt+\"*\") = 1)) then" writeToVBCode)
(write-line "item.service = \"Return Air (-6''WG) High Pressure\"" writeToVBCode)
(write-line "item.update()" writeToVBCode)
(write-line "elseif ((wildcard(item.service, \"*RETURN*\") = 1) and (wildcard(item.service, \"*10\"+qt+\"*\") = 1)) then" writeToVBCode)
(write-line "item.service = \"Return Air (-10''WG) High Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*2\"+qt+\"*\") = 1) or ((wildcard(item.specification, \"*-2*\") = 1) and (wildcard(item.specification, \"*WELD*\") = 0) and (wildcard(item.service, \"*None*\") = 1)) then" writeToVBCode)
(write-line "item.service = \"Exhaust Air (-2''WG) Low Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*3\"+qt+\"*\") = 1) or ((wildcard(item.specification, \"*-3*\") = 1) and (wildcard(item.specification, \"*WELD*\") = 0) and (wildcard(item.service, \"*None*\") = 1)) then" writeToVBCode)
(write-line "item.service = \"Exhaust Air (-3''WG) Medium Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*4\"+qt+\"*\") = 1) or ((wildcard(item.specification, \"*-4*\") = 1) and (wildcard(item.specification, \"*WELD*\") = 0) and (wildcard(item.service, \"*None*\") = 1)) then" writeToVBCode)
(write-line "item.service = \"Exhaust Air (-4''WG) High Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*6\"+qt+\"*\") = 1) or ((wildcard(item.specification, \"*-6*\") = 1) and (wildcard(item.specification, \"*WELD*\") = 0) and (wildcard(item.service, \"*None*\") = 1)) then" writeToVBCode)
(write-line "item.service = \"Exhaust Air (-6''WG) High Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*10\"+qt+\"*\") = 1) or ((wildcard(item.specification, \"*-10*\") = 1) and (wildcard(item.specification, \"*WELD*\") = 0) and (wildcard(item.service, \"*None*\") = 1)) then" writeToVBCode)
(write-line "item.service = \"Exhaust Air (-10''WG) High Pressure\"" writeToVBCode)
(write-line "item.update()" writeToVBCode)
(write-line "elseif ((wildcard(item.service, \"*EXHAUST*\") = 1) and (wildcard(item.service, \"*WELD*\") = 1) and (wildcard(item.service, \"*2\"+qt+\"*\") = 1)) or ((wildcard(item.specification, \"*WELD 2*\") = 1) and (wildcard(item.service, \"*None*\") = 1)) then" writeToVBCode)
(write-line "item.service = \"Exhaust Air Welded (-2''WG) Low Pressure\"" writeToVBCode)
(write-line "item.update()" writeToVBCode)
(write-line "elseif ((wildcard(item.service, \"*EXHAUST*\") = 1) and (wildcard(item.service, \"*WELD*\") = 1) and (wildcard(item.service, \"*3\"+qt+\"*\") = 1)) or ((wildcard(item.specification, \"*WELD 3*\") = 1) and (wildcard(item.service, \"*None*\") = 1)) then" writeToVBCode)
(write-line "item.service = \"Exhaust Air Welded (-3''WG) Medium Pressure\"" writeToVBCode)
(write-line "item.update()" writeToVBCode)
(write-line "elseif ((wildcard(item.service, \"*EXHAUST*\") = 1) and (wildcard(item.service, \"*WELD*\") = 1) and (wildcard(item.service, \"*4\"+qt+\"*\") = 1)) or ((wildcard(item.specification, \"*WELD 4*\") = 1) and (wildcard(item.service, \"*None*\") = 1)) then" writeToVBCode)
(write-line "item.service = \"Exhaust Air Welded (-4''WG) High Pressure\"" writeToVBCode)
(write-line "item.update()" writeToVBCode)
(write-line "elseif ((wildcard(item.service, \"*EXHAUST*\") = 1) and (wildcard(item.service, \"*WELD*\") = 1) and (wildcard(item.service, \"*6\"+qt+\"*\") = 1)) or ((wildcard(item.specification, \"*WELD 6*\") = 1) and (wildcard(item.service, \"*None*\") = 1)) then" writeToVBCode)
(write-line "item.service = \"Exhaust Air Welded (-6''WG) High Pressure\"" writeToVBCode)
(write-line "item.update()" writeToVBCode)
(write-line "elseif ((wildcard(item.service, \"*EXHAUST*\") = 1) and (wildcard(item.service, \"*WELD*\") = 1) and (wildcard(item.service, \"*10\"+qt+\"*\") = 1)) or ((wildcard(item.specification, \"*WELD 10*\") = 1) and (wildcard(item.service, \"*None*\") = 1)) then" writeToVBCode)
(write-line "item.service = \"Exhaust Air Welded (-10''WG) High Pressure\"" writeToVBCode)
(write-line "item.update()" writeToVBCode)
(write-line "elseif (wildcard(item.service, \"*EXHAUST*\") = 1) and (wildcard(item.service, \"*PVC*\") = 1) and (wildcard(item.service, \"*2\"+qt+\"*\") = 1) then" writeToVBCode)
(write-line "item.service = \"Exhaust Air PVC (-2''WG) Low Pressure\"" writeToVBCode)
(write-line "item.update()" writeToVBCode)
(write-line "elseif (wildcard(item.service, \"*COMBUSTION*\") = 1) and (wildcard(item.service, \"*2\"+qt+\"*\") = 1) then" writeToVBCode)
(write-line "item.service = \"Combustion Air (-2''WG) Low Pressure\"" writeToVBCode)
(write-line "item.update()" writeToVBCode)
(write-line "elseif (wildcard(item.service, \"*OUTSIDE*\") = 1) and (wildcard(item.service, \"*2\"+qt+\"*\") = 1) then" writeToVBCode)
(write-line "item.service = \"Outside Air (-2''WG) Low Pressure\"" writeToVBCode)
(write-line "item.update()" writeToVBCode)
(write-line "elseif (wildcard(item.service, \"*TRANSFER*\") = 1) and (wildcard(item.service, \"*2\"+qt+\"*\") = 1) then" writeToVBCode)
(write-line "item.service = \"Transfer Air (-2''WG) Low Pressure\"" writeToVBCode)
(write-line "item.update()" writeToVBCode)
(write-line "else" writeToVBCode)
(write-line "item.update()" writeToVBCode)
(write-line "end if" writeToVBCode)
(write-line "if (wildcard(item.service,\"*combustion*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*-10*\") = 1) and (wildcard(item.service,\"*weld*\") = 0) then" writeToVBCode)
(write-line "item.speclock = false" writeToVBCode)
(write-line "item.gaugelock = false" writeToVBCode)
(write-line "item.specification = \"-10''\"" writeToVBCode)
(write-line "item.speclock = true" writeToVBCode)
(write-line "item.update()" writeToVBCode)
(write-line "elseif (wildcard(item.service,\"*exhaust*\" + \"*-6*\") = 1) and (wildcard(item.service,\"*weld*\") = 0) then" writeToVBCode)
(write-line "item.speclock = false" writeToVBCode)
(write-line "item.gaugelock = false" writeToVBCode)
(write-line "item.specification = \"-6''\"" writeToVBCode)
(write-line "item.speclock = true" writeToVBCode)
(write-line "item.update()" writeToVBCode)
(write-line "elseif (wildcard(item.service,\"*exhaust*\" + \"*-4*\") = 1) and (wildcard(item.service,\"*weld*\") = 0) then" writeToVBCode)
(write-line "item.speclock = false" writeToVBCode)
(write-line "item.gaugelock = false" writeToVBCode)
(write-line "item.specification = \"-4''\"" writeToVBCode)
(write-line "item.speclock = true" writeToVBCode)
(write-line "item.update()" writeToVBCode)
(write-line "elseif (wildcard(item.service,\"*exhaust*\" + \"*inslab*\") = 1) and (wildcard(item.service,\"*weld*\") = 0) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*low*\") = 1) and (wildcard(item.service,\"*weld*\") = 0) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*medium*\") = 1) and (wildcard(item.service,\"*weld*\") = 0) then" writeToVBCode)
(write-line "item.speclock = false" writeToVBCode)
(write-line "item.gaugelock = false" writeToVBCode)
(write-line "item.specification = \"-3''\"" writeToVBCode)
(write-line "item.speclock = true" writeToVBCode)
(write-line "item.update()" writeToVBCode)
(write-line "elseif (wildcard(item.service,\"*exhaust*\" + \"*weld*\" + \"*-10*\") = 1) then" writeToVBCode)
(write-line "item.speclock = false" writeToVBCode)
(write-line "item.gaugelock = false" writeToVBCode)
(write-line "item.specification = \"WELD 10\" + qt + \" 5FT\"" writeToVBCode)
(write-line "item.speclock = true" writeToVBCode)
(write-line "item.update()" writeToVBCode)
(write-line "elseif (wildcard(item.service,\"*exhaust*\" + \"*weld*\" + \"*-6*\") = 1) then" writeToVBCode)
(write-line "item.speclock = false" writeToVBCode)
(write-line "item.gaugelock = false" writeToVBCode)
(write-line "item.specification = \"WELD 6\" + qt + \" 5FT\"" writeToVBCode)
(write-line "item.speclock = true" writeToVBCode)
(write-line "item.update()" writeToVBCode)
(write-line "elseif (wildcard(item.service,\"*exhaust*\" + \"*weld*\" + \"*-4*\") = 1) then" writeToVBCode)
(write-line "item.speclock = false" writeToVBCode)
(write-line "item.gaugelock = false" writeToVBCode)
(write-line "item.specification = \"WELD 4\" + qt + \" 5FT\"" writeToVBCode)
(write-line "item.speclock = true" writeToVBCode)
(write-line "item.update()" writeToVBCode)
(write-line "elseif (wildcard(item.service,\"*exhaust*\" + \"*weld*\" + \"*-2*\") = 1) then" writeToVBCode)
(write-line "item.speclock = false" writeToVBCode)
(write-line "item.gaugelock = false" writeToVBCode)
(write-line "item.specification = \"WELD 2\" + qt + \" 5FT\"" writeToVBCode)
(write-line "item.speclock = true" writeToVBCode)
(write-line "item.update()" writeToVBCode)
(write-line "elseif (wildcard(item.service,\"*outside*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*return*\" + \"*-10*\") = 1) then" writeToVBCode)
(write-line "item.speclock = false" writeToVBCode)
(write-line "item.gaugelock = false" writeToVBCode)
(write-line "item.specification = \"-10''\"" writeToVBCode)
(write-line "item.speclock = true" writeToVBCode)
(write-line "item.update()" writeToVBCode)
(write-line "elseif (wildcard(item.service,\"*return*\" + \"*-6*\") = 1) then" writeToVBCode)
(write-line "item.speclock = false" writeToVBCode)
(write-line "item.gaugelock = false" writeToVBCode)
(write-line "item.specification = \"-6''\"" writeToVBCode)
(write-line "item.speclock = true" writeToVBCode)
(write-line "item.update()" writeToVBCode)
(write-line "elseif (wildcard(item.service,\"*return*\" + \"*-4*\") = 1) then" writeToVBCode)
(write-line "item.speclock = false" writeToVBCode)
(write-line "item.gaugelock = false" writeToVBCode)
(write-line "item.specification = \"-4''\"" writeToVBCode)
(write-line "item.speclock = true" writeToVBCode)
(write-line "item.update()" writeToVBCode)
(write-line "elseif (wildcard(item.service,\"*return*\" + \"*-2*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*return*\" + \"*medium*\") = 1) then" writeToVBCode)
(write-line "item.speclock = false" writeToVBCode)
(write-line "item.gaugelock = false" writeToVBCode)
(write-line "item.specification = \"-3''\"" writeToVBCode)
(write-line "item.speclock = true" writeToVBCode)
(write-line "item.update()" writeToVBCode)
(write-line "elseif (wildcard(item.service,\"*supply*\" + \"*+10*\") = 1) then" writeToVBCode)
(write-line "item.speclock = false" writeToVBCode)
(write-line "item.gaugelock = false" writeToVBCode)
(write-line "item.specification = \"+10''\"" writeToVBCode)
(write-line "item.speclock = true" writeToVBCode)
(write-line "item.update()" writeToVBCode)
(write-line "elseif (wildcard(item.service,\"*supply*\" + \"*+6*\") = 1) then" writeToVBCode)
(write-line "item.speclock = false" writeToVBCode)
(write-line "item.gaugelock = false" writeToVBCode)
(write-line "item.specification = \"+6''\"" writeToVBCode)
(write-line "item.speclock = true" writeToVBCode)
(write-line "item.update()" writeToVBCode)
(write-line "elseif (wildcard(item.service,\"*supply*\" + \"*+4*\") = 1) then" writeToVBCode)
(write-line "item.speclock = false" writeToVBCode)
(write-line "item.gaugelock = false" writeToVBCode)
(write-line "item.specification = \"+4''\"" writeToVBCode)
(write-line "item.speclock = true" writeToVBCode)
(write-line "item.update()" writeToVBCode)
(write-line "elseif (wildcard(item.service,\"*supply*\" + \"*medium*\") = 1) then" writeToVBCode)
(write-line "item.speclock = false" writeToVBCode)
(write-line "item.gaugelock = false" writeToVBCode)
(write-line "item.specification = \"+3''\"" writeToVBCode)
(write-line "item.speclock = true" writeToVBCode)
(write-line "item.update()" writeToVBCode)
(write-line "elseif (wildcard(item.service,\"*supply*\" + \"*low*\") = 1) then" writeToVBCode)
(write-line "item.speclock = false" writeToVBCode)
(write-line "item.gaugelock = false" writeToVBCode)
(write-line "item.specification = \"+2''\"" writeToVBCode)
(write-line "item.speclock = true" writeToVBCode)
(write-line "item.update()" writeToVBCode)
(write-line "elseif (wildcard(item.service,\"*transfer*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "end if" writeToVBCode)
(write-line "i = i + 1" writeToVBCode)
(write-line "end while" writeToVBCode)
    (princ)
    (close writeToVBCode)
    (executescript vbCode sset)
    (terpri)(princ "-- Services and Specifications Updated")(princ)
    );progn
  );end if
(progn
  (if(>= (distof acadVersionYear) 2019)
    (progn
      (terpri)(prompt "Updating Activity Numbers and ItemCIDs for all items --")(princ)
    (while(< i limit)
    (INSIDE_LOOP_VARIABLES sset i)
    (if(or(wcmatch(strcase ItemServiceType)(strcase "*Equipment*"))
        (wcmatch(strcase ItemSourceFileName)(strcase "*Diffuser*"))
        (wcmatch(strcase ItemSourceFileName)(strcase "*Register*"))
        (wcmatch(strcase ItemSourceFileName)(strcase "*Grille*"))
        (wcmatch(strcase ItemSourceFileName)(strcase "*Titus*")))
    (setq Activity# "75")
    (if(or(wcmatch(strcase ItemServiceType)(strcase "*Fire Damper*"))
          (wcmatch(strcase ItemDescription)(strcase "*Canvas*"))
          (wcmatch(strcase ItemDescription)(strcase "*Access Door*"))
          (wcmatch(strcase ItemDescription)(strcase "*Damper Sleeve*"))
          (wcmatch(strcase ItemDescription)(strcase "*Plate*"))
          (and(wcmatch(strcase ItemSourceFileName)(strcase "*Angle*"))(not(wcmatch(strcase ItemSourceFileName)(strcase "*Rectangle*"))))
          (wcmatch(strcase ItemSourceFileName)(strcase "*Can*")))
      (setq Activity# "302")
      (if(or allSupport (wcmatch(strcase ItemServiceType)(strcase "*Hanger*")))
        (setq Activity# "303")
    (if(and(wcmatch(strcase ItemServiceType)(strcase "*Ductboard*"))
          (wcmatch(strcase ItemSourceFileName)(strcase "*Straight*")))
      (setq Activity# "304")
    (if(and(wcmatch(strcase ItemServiceType)(strcase "*Ductboard*"))
          (not(wcmatch(strcase ItemSourceFileName)(strcase "*Straight*"))))
      (setq Activity# "305")
        (if(and(not(or(wcmatch(strcase ItemService)(strcase "*Weld*"))(wcmatch(strcase ItemServiceType)(strcase "*Equipment*"))))
           (or
           (and(wcmatch(strcase ItemSourceFileName)(strcase "Straight"))
                       (or(wcmatch(strcase c1Name)(strcase "TDF*"))
                          (wcmatch(strcase c2Name)(strcase "TDF*"))
                          (wcmatch(strcase c1Name)(strcase "*JF*"))
                          (wcmatch(strcase c2Name)(strcase "*JF*")))
               (>= ItemLengthAngle 56))
           (and(wcmatch(strcase ItemSourceFileName)(strcase "Straight"))
               (or(wcmatch(strcase c1Name)(strcase "Stand S&D"))
                  (wcmatch(strcase c1Name)(strcase "Flat S&D"))
                  (wcmatch(strcase c2Name)(strcase "Stand S&D"))
                  (wcmatch(strcase c2Name)(strcase "Flat S&D"))
                  (wcmatch(strcase c1Name)(strcase "*S&D*"))
                  (wcmatch(strcase c2Name)(strcase "*S&D*")))
               (>= ItemLengthAngle 59))
          ))
          (setq Activity# "310")
          (if(wcmatch(strcase ItemSourceFileName)(strcase "*SPIRAL"))
            (setq Activity# "312")
            (if(and(not(or(wcmatch(strcase ItemService)(strcase "*Weld*"))(wcmatch(strcase ItemServiceType)(strcase "*Equipment*"))))
               (or
               (wcmatch(strcase ItemSourceFileName)(strcase "*Pipe*"))
               (and
               (= ItemLengthAngle 18)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*8/6/6*"))
                  (wcmatch(strcase ItemDescription)(strcase "*10/8/6*"))
                  (wcmatch(strcase ItemDescription)(strcase "*10/8/8*"))
                  (wcmatch(strcase ItemDescription)(strcase "*12/8/6*"))
                  (wcmatch(strcase ItemDescription)(strcase "*12/8/8*"))
                  (wcmatch(strcase ItemDescription)(strcase "*12/10/6*"))
                  (wcmatch(strcase ItemDescription)(strcase "*12/10/8*"))
                  (wcmatch(strcase ItemDescription)(strcase "*12/10/10*"))
                  (wcmatch(strcase ItemDescription)(strcase "*14/10/8*"))
                  (wcmatch(strcase ItemDescription)(strcase "*14/10/10*"))
                  (wcmatch(strcase ItemDescription)(strcase "*14/12/6*"))
                  (wcmatch(strcase ItemDescription)(strcase "*14/12/8*"))
                  (wcmatch(strcase ItemDescription)(strcase "*14/12/10*"))
                  (wcmatch(strcase ItemDescription)(strcase "*16/10/10*"))
                  (wcmatch(strcase ItemDescription)(strcase "*16/12/8*"))
                  (wcmatch(strcase ItemDescription)(strcase "*16/12/10*"))
                  (wcmatch(strcase ItemDescription)(strcase "*16/14/8*"))
                  (wcmatch(strcase ItemDescription)(strcase "*16/14/10*")))
               )
               (and
               (= ItemLengthAngle 20)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*14/12/12*"))
                  (wcmatch(strcase ItemDescription)(strcase "*16/12/12*"))
                  (wcmatch(strcase ItemDescription)(strcase "*16/14/12*")))
               )
               (and
               (= ItemLengthAngle 30)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*16/14/14*"))
                  (wcmatch(strcase ItemDescription)(strcase "*18/14/14*")))
               )
               (and
               (= ItemLengthAngle 18)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*6/6/6*"))
               (wcmatch(strcase ItemDescription)(strcase "*8/8/8*"))
               (wcmatch(strcase ItemDescription)(strcase "*10/10/6*"))
               (wcmatch(strcase ItemDescription)(strcase "*10/10/8*"))
               (wcmatch(strcase ItemDescription)(strcase "*10/10/10*"))
               (wcmatch(strcase ItemDescription)(strcase "*12/12/6*"))
               (wcmatch(strcase ItemDescription)(strcase "*12/12/8*"))
               (wcmatch(strcase ItemDescription)(strcase "*12/12/10*"))
               (wcmatch(strcase ItemDescription)(strcase "*14/14/6*"))
               (wcmatch(strcase ItemDescription)(strcase "*14/14/8*"))
               (wcmatch(strcase ItemDescription)(strcase "*14/14/10*"))
               (wcmatch(strcase ItemDescription)(strcase "*16/16/8*")))
               )
               (and
               (= ItemLengthAngle 20)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*12/12/12*"))
               (wcmatch(strcase ItemDescription)(strcase "*14/14/12*")))
               )
               (and
               (= ItemLengthAngle 30)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*14/14/14*")))
               )
               (and
               (wcmatch ItemCID "60")
               (wcmatch(strcase ItemSourceFileName)(strcase "*Cap*"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (wcmatch ItemCID "60")
               (wcmatch(strcase ItemSourceFileName)(strcase "*End Cap*"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (wcmatch ItemCID "1112")
               (wcmatch(strcase ItemDescription)(strcase "*3\" Collar*"))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*"))
                  (wcmatch(strcase ItemDescription)(strcase "*20\"*")))
               )
               (and
               (wcmatch ItemCID "1112")
               (wcmatch(strcase ItemDescription)(strcase "*Spin-in*"))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*")))
               )
               (and
                  (wcmatch(strcase ItemDescription)(strcase "*6\" Long Taper*"))
               (or(wcmatch(strcase ItemDescription)(strcase "*7-5*"))
                  (wcmatch(strcase ItemDescription)(strcase "*8-6*"))
                  (wcmatch(strcase ItemDescription)(strcase "*9-7*"))
                  (wcmatch(strcase ItemDescription)(strcase "*10-8*"))
                  (wcmatch(strcase ItemDescription)(strcase "*10-9*"))
                  (wcmatch(strcase ItemDescription)(strcase "*12-10*"))
                  (wcmatch(strcase ItemDescription)(strcase "*14-12*"))
                  (wcmatch(strcase ItemDescription)(strcase "*16-14*"))
                  (wcmatch(strcase ItemDescription)(strcase "*18-16*")))
               )
               (and
                  (wcmatch(strcase ItemDescription)(strcase "*12\" Long Taper*"))
               (or(wcmatch(strcase ItemDescription)(strcase "*10-6*"))
                  (wcmatch(strcase ItemDescription)(strcase "*12-8*"))
                  (wcmatch(strcase ItemDescription)(strcase "*14-10*"))
                  (wcmatch(strcase ItemDescription)(strcase "*16-12*"))
                  (wcmatch(strcase ItemDescription)(strcase "*18-14*"))
                  (wcmatch(strcase ItemDescription)(strcase "*8-5*"))
                  (wcmatch(strcase ItemDescription)(strcase "*7-6*"))
                  (wcmatch(strcase ItemDescription)(strcase "*9-6*"))
                  (wcmatch(strcase ItemDescription)(strcase "*8-7*"))
                  (wcmatch(strcase ItemDescription)(strcase "*9-7*"))
                  (wcmatch(strcase ItemDescription)(strcase "*10-7*"))
                  (wcmatch(strcase ItemDescription)(strcase "*12-7*"))
                  (wcmatch(strcase ItemDescription)(strcase "*10-9*"))
                  (wcmatch(strcase ItemDescription)(strcase "*12-6*"))
                  (wcmatch(strcase ItemDescription)(strcase "*12-10*"))
                  (wcmatch(strcase ItemDescription)(strcase "*18-10*")))
               )
               (and
                  (wcmatch(strcase ItemDescription)(strcase "*18\" Long Taper*"))
               (or(wcmatch(strcase ItemDescription)(strcase "*12-6*"))
                  (wcmatch(strcase ItemDescription)(strcase "*14-6*"))
                  (wcmatch(strcase ItemDescription)(strcase "*12-8*"))
                  (wcmatch(strcase ItemDescription)(strcase "*14-8*"))
                  (wcmatch(strcase ItemDescription)(strcase "*16-8*"))
                  (wcmatch(strcase ItemDescription)(strcase "*16-12*"))
                  (wcmatch(strcase ItemDescription)(strcase "*18-12*"))
                  (wcmatch(strcase ItemDescription)(strcase "*16-14*"))
                  (wcmatch(strcase ItemDescription)(strcase "*18-14*"))
                  (wcmatch(strcase ItemDescription)(strcase "*20-14*"))
                  (wcmatch(strcase ItemDescription)(strcase "*18-16*"))
                  (wcmatch(strcase ItemDescription)(strcase "*20-18*"))
                  (wcmatch(strcase ItemDescription)(strcase "*6-5*"))
                  (wcmatch(strcase ItemDescription)(strcase "*7-6*"))
                  (wcmatch(strcase ItemDescription)(strcase "*8-7*"))
                  (wcmatch(strcase ItemDescription)(strcase "*9-8*"))
                  (wcmatch(strcase ItemDescription)(strcase "*10-9*"))
                  (wcmatch(strcase ItemDescription)(strcase "*9-6*"))
                  (wcmatch(strcase ItemDescription)(strcase "*9-7*"))
                  (wcmatch(strcase ItemDescription)(strcase "*10-7*"))
                  (wcmatch(strcase ItemDescription)(strcase "*12-7*"))
                  (wcmatch(strcase ItemDescription)(strcase "*14-7*"))
                  (wcmatch(strcase ItemDescription)(strcase "*12-9*"))
                  (wcmatch(strcase ItemDescription)(strcase "*14-9*")))
               )
               (and
               (or(wcmatch(strcase ItemSourceFileName)(strcase "*45Deg on Rd Saddle*"))
                  (wcmatch(strcase ItemDescription)(strcase "*45 Deg Sad*"))
                  (wcmatch ItemCID "875"))
               (or(wcmatch(strcase ItemDescription)(strcase "*6\" on 6\"*"))
                  (wcmatch(strcase ItemDescription)(strcase "*6 on 6*"))
                  (wcmatch(strcase ItemDescription)(strcase "*6\" on 8\"*"))
                  (wcmatch(strcase ItemDescription)(strcase "*6 on 8*"))
                  (wcmatch(strcase ItemDescription)(strcase "*6\" on 10\"*"))
                  (wcmatch(strcase ItemDescription)(strcase "*6 on 10*"))
                  (wcmatch(strcase ItemDescription)(strcase "*6\" on 12\"*"))
                  (wcmatch(strcase ItemDescription)(strcase "*6 on 12*"))
                  (wcmatch(strcase ItemDescription)(strcase "*6\" on 14\"*"))
                  (wcmatch(strcase ItemDescription)(strcase "*6 on 14*"))
                  (wcmatch(strcase ItemDescription)(strcase "*6\" on 16\"*"))
                  (wcmatch(strcase ItemDescription)(strcase "*6 on 16*"))
                  (wcmatch(strcase ItemDescription)(strcase "*6\" on 18\"*"))
                  (wcmatch(strcase ItemDescription)(strcase "*6 on 18*"))
                  (wcmatch(strcase ItemDescription)(strcase "*8\" on 8\"*"))
                  (wcmatch(strcase ItemDescription)(strcase "*8 on 8*"))
                  (wcmatch(strcase ItemDescription)(strcase "*8\" on 10\"*"))
                  (wcmatch(strcase ItemDescription)(strcase "*8 on 10*"))
                  (wcmatch(strcase ItemDescription)(strcase "*8\" on 12\"*"))
                  (wcmatch(strcase ItemDescription)(strcase "*8 on 12*"))
                  (wcmatch(strcase ItemDescription)(strcase "*8\" on 14\"*"))
                  (wcmatch(strcase ItemDescription)(strcase "*8 on 14*"))
                  (wcmatch(strcase ItemDescription)(strcase "*8\" on 16\"*"))
                  (wcmatch(strcase ItemDescription)(strcase "*8 on 16*"))
                  (wcmatch(strcase ItemDescription)(strcase "*8\" on 18\"*"))
                  (wcmatch(strcase ItemDescription)(strcase "*8 on 18*"))
                  (wcmatch(strcase ItemDescription)(strcase "*10\" on 10\"*"))
                  (wcmatch(strcase ItemDescription)(strcase "*10 on 10*"))
                  (wcmatch(strcase ItemDescription)(strcase "*10\" on 12\"*"))
                  (wcmatch(strcase ItemDescription)(strcase "*10 on 12*"))
                  (wcmatch(strcase ItemDescription)(strcase "*10\" on 14\"*"))
                  (wcmatch(strcase ItemDescription)(strcase "*10 on 14*"))
                  (wcmatch(strcase ItemDescription)(strcase "*10\" on 16\"*"))
                  (wcmatch(strcase ItemDescription)(strcase "*10 on 16*"))
                  (wcmatch(strcase ItemDescription)(strcase "*10\" on 18\"*"))
                  (wcmatch(strcase ItemDescription)(strcase "*10 on 18*"))
                  (wcmatch(strcase ItemDescription)(strcase "*10\" on 20\"*"))
                  (wcmatch(strcase ItemDescription)(strcase "*10 on 20*"))
                  (wcmatch(strcase ItemDescription)(strcase "*14\" on 14\"*"))
                  (wcmatch(strcase ItemDescription)(strcase "*14 on 14*"))
                  (wcmatch(strcase ItemDescription)(strcase "*14\" on 16\"*"))
                  (wcmatch(strcase ItemDescription)(strcase "*14 on 16*")))
               )
               (and
               (or(wcmatch(strcase ItemSourceFileName)(strcase "*45Deg Flat Saddle*"))
                  (wcmatch(strcase ItemDescription)(strcase "*45D Flat*"))
                  (wcmatch ItemCID "16"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*")))
               )
               (and
               (or(wcmatch(strcase ItemSourceFileName)(strcase "*Rd on Rd Conical*"))
                  (wcmatch(strcase ItemDescription)(strcase "*#8 *"))
                  (wcmatch ItemCID "751"))
               (or(wcmatch(strcase ItemDescription)(strcase "*6\" on 8\"*"))
                  (wcmatch(strcase ItemDescription)(strcase "*6 on 8*"))
                  (wcmatch(strcase ItemDescription)(strcase "*6\" on 10\"*"))
                  (wcmatch(strcase ItemDescription)(strcase "*6 on 10*"))
                  (wcmatch(strcase ItemDescription)(strcase "*6\" on 12\"*"))
                  (wcmatch(strcase ItemDescription)(strcase "*6 on 12*"))
                  (wcmatch(strcase ItemDescription)(strcase "*6\" on 14\"*"))
                  (wcmatch(strcase ItemDescription)(strcase "*6 on 14*"))
                  (wcmatch(strcase ItemDescription)(strcase "*6\" on 16\"*"))
                  (wcmatch(strcase ItemDescription)(strcase "*6 on 16*"))
                  (wcmatch(strcase ItemDescription)(strcase "*6\" on 18\"*"))
                  (wcmatch(strcase ItemDescription)(strcase "*6 on 18*"))
                  (wcmatch(strcase ItemDescription)(strcase "*6\" on 20\"*"))
                  (wcmatch(strcase ItemDescription)(strcase "*6 on 20*"))
                  (wcmatch(strcase ItemDescription)(strcase "*8\" on 10\"*"))
                  (wcmatch(strcase ItemDescription)(strcase "*8 on 10*"))
                  (wcmatch(strcase ItemDescription)(strcase "*8\" on 12\"*"))
                  (wcmatch(strcase ItemDescription)(strcase "*8 on 12*"))
                  (wcmatch(strcase ItemDescription)(strcase "*8\" on 14\"*"))
                  (wcmatch(strcase ItemDescription)(strcase "*8 on 14*"))
                  (wcmatch(strcase ItemDescription)(strcase "*8\" on 16\"*"))
                  (wcmatch(strcase ItemDescription)(strcase "*8 on 16*"))
                  (wcmatch(strcase ItemDescription)(strcase "*8\" on 18\"*"))
                  (wcmatch(strcase ItemDescription)(strcase "*8 on 18*"))
                  (wcmatch(strcase ItemDescription)(strcase "*10\" on 12\"*"))
                  (wcmatch(strcase ItemDescription)(strcase "*10 on 12*"))
                  (wcmatch(strcase ItemDescription)(strcase "*10\" on 14\"*"))
                  (wcmatch(strcase ItemDescription)(strcase "*10 on 14*"))
                  (wcmatch(strcase ItemDescription)(strcase "*10\" on 16\"*"))
                  (wcmatch(strcase ItemDescription)(strcase "*10 on 16*"))
                  (wcmatch(strcase ItemDescription)(strcase "*10\" on 18\"*"))
                  (wcmatch(strcase ItemDescription)(strcase "*10 on 18*"))
                  (wcmatch(strcase ItemDescription)(strcase "*12\" on 14\"*"))
                  (wcmatch(strcase ItemDescription)(strcase "*12 on 14*"))
                  (wcmatch(strcase ItemDescription)(strcase "*12\" on 16\"*"))
                  (wcmatch(strcase ItemDescription)(strcase "*12 on 16*"))
                  (wcmatch(strcase ItemDescription)(strcase "*12\" on 18\"*"))
                  (wcmatch(strcase ItemDescription)(strcase "*12 on 18*"))
                  (wcmatch(strcase ItemDescription)(strcase "*12\" on 20\"*"))
                  (wcmatch(strcase ItemDescription)(strcase "*12 on 20*"))
                  (wcmatch(strcase ItemDescription)(strcase "*14\" on 16\"*"))
                  (wcmatch(strcase ItemDescription)(strcase "*14 on 16*"))
                  (wcmatch(strcase ItemDescription)(strcase "*14\" on 18\"*"))
                  (wcmatch(strcase ItemDescription)(strcase "*14 on 18*")))
               )
               (and
               (or(wcmatch(strcase ItemSourceFileName)(strcase "*Round Access Door*"))
                  (wcmatch(strcase ItemSourceFileName)(strcase "*#7 Access Door*")))
               (or(wcmatch(strcase ItemDescription)(strcase "*6\"*"))
                  (wcmatch(strcase ItemDescription)(strcase "*8\"*"))
                  (wcmatch(strcase ItemDescription)(strcase "*10\"*"))
                  (wcmatch(strcase ItemDescription)(strcase "*12\"*"))
                  (wcmatch(strcase ItemDescription)(strcase "*14\"*")))
               )
               (and
               (or(wcmatch(strcase ItemSourceFileName)(strcase "*Conical Flat Tap*"))
                  (wcmatch(strcase ItemSourceFileName)(strcase "*Flat Conical 1\" Flg*"))
                  (wcmatch ItemCID "345"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(and(wcmatch ItemCID "51")(wcmatch(strcase ItemSourceFileName)(strcase "*6\" Start Collar wFlg*"))(wcmatch(strcase ItemDescription)(strcase "*for Damper*")))
                  (and(wcmatch ItemCID "51")(wcmatch(strcase ItemDescription)(strcase "*Damper*"))))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(and(wcmatch ItemCID "51")(wcmatch(strcase ItemSourceFileName)(strcase "*6\" Start Collar wFlg*"))(not(wcmatch(strcase ItemDescription)(strcase "*for Damper*"))))
                  (and(wcmatch ItemCID "51")(not(wcmatch(strcase ItemDescription)(strcase "*Damper*")))))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*")))
               )
               (and
               (or(wcmatch(strcase ItemSourceFileName)(strcase "Coupling")))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(wcmatch ItemCID "522")
                  (wcmatch(strcase ItemSourceFileName)(strcase "#2 Coupling")))
               (or(= dim1 6)
                  (= dim1 7)
                  (= dim1 8)
                  (= dim1 9)
                  (= dim1 10)
                  (= dim1 12)
                  (= dim1 14)
                  (= dim1 16)
                  (= dim1 18)
                  (= dim1 20))
               )
               )
               )
              (setq Activity# "316")
            (if(and(not(or(wcmatch(strcase ItemService)(strcase "*Weld*"))(wcmatch(strcase ItemServiceType)(strcase "*Equipment*"))))
               (or
                 (or(wcmatch(strcase ItemSourceFileName)(strcase "*Conical Cross*"))
                    (wcmatch(strcase ItemSourceFileName)(strcase "*Conical Tee*"))
                    (wcmatch(strcase ItemSourceFileName)(strcase "*90 Adj.*"))
                    (wcmatch(strcase ItemSourceFileName)(strcase "*45 Adj.*"))
                    (wcmatch(strcase ItemSourceFileName)(strcase "*Misc. Elbow*"))
                    (wcmatch(strcase ItemSourceFileName)(strcase "*Welded Elbow*"))
                    (wcmatch(strcase ItemSourceFileName)(strcase "*90Deg Adj.*"))
                    (wcmatch(strcase ItemSourceFileName)(strcase "*45Deg Adj.*"))
                    (wcmatch(strcase ItemSourceFileName)(strcase "Misc. Adj. Elbow*"))
                    (wcmatch(strcase ItemSourceFileName)(strcase "Misc. Adjustable Elbow*"))
                    (wcmatch(strcase ItemSourceFileName)(strcase "Misc. El*"))
                    (wcmatch(strcase ItemSourceFileName)(strcase "*Shoe Barrel*"))
                    (wcmatch(strcase ItemSourceFileName)(strcase "*Shoe Saddle*"))
                    (wcmatch(strcase ItemSourceFileName)(strcase "*Mitered Offset Fixed*"))
                    (wcmatch(strcase ItemSourceFileName)(strcase "*Deflector Hood*"))
                    (wcmatch(strcase ItemSourceFileName)(strcase "*FULL RAD.*"))
                    (wcmatch(strcase ItemSourceFileName)(strcase "*HALF RAD.*"))
                    (wcmatch(strcase ItemSourceFileName)(strcase "*Pancake*"))
                    (wcmatch(strcase ItemSourceFileName)(strcase "*Flex*"))
                    (wcmatch(strcase ItemSourceFileName)(strcase "*Welded Pipe*"))
                    (wcmatch(strcase ItemDescription)(strcase "* CROSS*"))
                 )
                 (and
                 (= ItemLengthAngle 18)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*8/6/6*"))
                    (wcmatch(strcase ItemDescription)(strcase "*10/8/6*"))
                    (wcmatch(strcase ItemDescription)(strcase "*10/8/8*"))
                    (wcmatch(strcase ItemDescription)(strcase "*12/8/6*"))
                    (wcmatch(strcase ItemDescription)(strcase "*12/8/8*"))
                    (wcmatch(strcase ItemDescription)(strcase "*12/10/6*"))
                    (wcmatch(strcase ItemDescription)(strcase "*12/10/8*"))
                    (wcmatch(strcase ItemDescription)(strcase "*12/10/10*"))
                    (wcmatch(strcase ItemDescription)(strcase "*14/10/8*"))
                    (wcmatch(strcase ItemDescription)(strcase "*14/10/10*"))
                    (wcmatch(strcase ItemDescription)(strcase "*14/12/6*"))
                    (wcmatch(strcase ItemDescription)(strcase "*14/12/8*"))
                    (wcmatch(strcase ItemDescription)(strcase "*14/12/10*"))
                    (wcmatch(strcase ItemDescription)(strcase "*16/10/10*"))
                    (wcmatch(strcase ItemDescription)(strcase "*16/12/8*"))
                    (wcmatch(strcase ItemDescription)(strcase "*16/12/10*"))
                    (wcmatch(strcase ItemDescription)(strcase "*16/14/8*"))
                    (wcmatch(strcase ItemDescription)(strcase "*16/14/10*"))))
                 )
                 (and
                 (= ItemLengthAngle 20)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*14/12/12*"))
                    (wcmatch(strcase ItemDescription)(strcase "*16/12/12*"))
                    (wcmatch(strcase ItemDescription)(strcase "*16/14/12*"))))
                 )
                 (and
                 (= ItemLengthAngle 30)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*16/14/14*"))
                    (wcmatch(strcase ItemDescription)(strcase "*18/14/14*"))))
                 )
                 (and
                 (= ItemLengthAngle 18)
                 (or(wcmatch(strcase ItemSourceFileName)(strcase "*Lateral 45*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*6/6/6*"))
                 (wcmatch(strcase ItemDescription)(strcase "*8/8/8*"))
                 (wcmatch(strcase ItemDescription)(strcase "*10/10/6*"))
                 (wcmatch(strcase ItemDescription)(strcase "*10/10/8*"))
                 (wcmatch(strcase ItemDescription)(strcase "*10/10/10*"))
                 (wcmatch(strcase ItemDescription)(strcase "*12/12/6*"))
                 (wcmatch(strcase ItemDescription)(strcase "*12/12/8*"))
                 (wcmatch(strcase ItemDescription)(strcase "*12/12/10*"))
                 (wcmatch(strcase ItemDescription)(strcase "*14/14/6*"))
                 (wcmatch(strcase ItemDescription)(strcase "*14/14/8*"))
                 (wcmatch(strcase ItemDescription)(strcase "*14/14/10*"))
                 (wcmatch(strcase ItemDescription)(strcase "*16/16/8*"))))
                 )
                 (and
                 (= ItemLengthAngle 20)
                 (or(wcmatch(strcase ItemSourceFileName)(strcase "*Lateral 45*"))
                 (wcmatch(strcase ItemSourceFileName)(strcase "*No Dampers*"))
                 (wcmatch(strcase ItemSourceFileName)(strcase "*KS7L*"))
                 (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*12/12/12*"))
                 (wcmatch(strcase ItemDescription)(strcase "*14/14/12*"))))
                 )
                 (and
                 (= ItemLengthAngle 30)
                 (or(wcmatch(strcase ItemSourceFileName)(strcase "*Lateral 45*"))
                 (wcmatch(strcase ItemSourceFileName)(strcase "*No Dampers*"))
                 (wcmatch(strcase ItemSourceFileName)(strcase "*KS7L*"))
                 (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*14/14/14*"))))
                 )
                 (and(wcmatch ItemCID "60")
                     (wcmatch(strcase ItemSourceFileName)(strcase "*Cap*"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and(wcmatch ItemCID "60")
                     (wcmatch(strcase ItemSourceFileName)(strcase "*End Cap*"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and(wcmatch ItemCID "1112")
                     (wcmatch(strcase ItemDescription)(strcase "*3\" Collar*"))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))
                    (wcmatch(strcase ItemDescription)(strcase "*20\"*"))))
                 )
                 (and(wcmatch ItemCID "1112")
                     (wcmatch(strcase ItemDescription)(strcase "*Spin-in*"))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))))
                 )
                 (and(wcmatch(strcase ItemDescription)(strcase "*6\" Long Taper*"))
                 (not(or(wcmatch(strcase ItemDescription)(strcase "*7-5*"))
                    (wcmatch(strcase ItemDescription)(strcase "*8-6*"))
                    (wcmatch(strcase ItemDescription)(strcase "*9-7*"))
                    (wcmatch(strcase ItemDescription)(strcase "*10-8*"))
                    (wcmatch(strcase ItemDescription)(strcase "*10-9*"))
                    (wcmatch(strcase ItemDescription)(strcase "*12-10*"))
                    (wcmatch(strcase ItemDescription)(strcase "*14-12*"))
                    (wcmatch(strcase ItemDescription)(strcase "*16-14*"))
                    (wcmatch(strcase ItemDescription)(strcase "*18-16*"))))
                 )
                 (and(wcmatch(strcase ItemDescription)(strcase "*12\" Long Taper*"))
                 (not(or(wcmatch(strcase ItemDescription)(strcase "*10-6*"))
                    (wcmatch(strcase ItemDescription)(strcase "*12-8*"))
                    (wcmatch(strcase ItemDescription)(strcase "*14-10*"))
                    (wcmatch(strcase ItemDescription)(strcase "*16-12*"))
                    (wcmatch(strcase ItemDescription)(strcase "*18-14*"))
                    (wcmatch(strcase ItemDescription)(strcase "*8-5*"))
                    (wcmatch(strcase ItemDescription)(strcase "*7-6*"))
                    (wcmatch(strcase ItemDescription)(strcase "*9-6*"))
                    (wcmatch(strcase ItemDescription)(strcase "*8-7*"))
                    (wcmatch(strcase ItemDescription)(strcase "*9-7*"))
                    (wcmatch(strcase ItemDescription)(strcase "*10-7*"))
                    (wcmatch(strcase ItemDescription)(strcase "*12-7*"))
                    (wcmatch(strcase ItemDescription)(strcase "*10-9*"))
                    (wcmatch(strcase ItemDescription)(strcase "*12-6*"))
                    (wcmatch(strcase ItemDescription)(strcase "*12-10*"))
                    (wcmatch(strcase ItemDescription)(strcase "*18-10*"))))
                 )
                 (and(wcmatch(strcase ItemDescription)(strcase "*18\" Long Taper*"))
                 (not(or(wcmatch(strcase ItemDescription)(strcase "*12-6*"))
                    (wcmatch(strcase ItemDescription)(strcase "*14-6*"))
                    (wcmatch(strcase ItemDescription)(strcase "*12-8*"))
                    (wcmatch(strcase ItemDescription)(strcase "*14-8*"))
                    (wcmatch(strcase ItemDescription)(strcase "*16-8*"))
                    (wcmatch(strcase ItemDescription)(strcase "*16-12*"))
                    (wcmatch(strcase ItemDescription)(strcase "*18-12*"))
                    (wcmatch(strcase ItemDescription)(strcase "*16-14*"))
                    (wcmatch(strcase ItemDescription)(strcase "*18-14*"))
                    (wcmatch(strcase ItemDescription)(strcase "*20-14*"))
                    (wcmatch(strcase ItemDescription)(strcase "*18-16*"))
                    (wcmatch(strcase ItemDescription)(strcase "*20-18*"))
                    (wcmatch(strcase ItemDescription)(strcase "*6-5*"))
                    (wcmatch(strcase ItemDescription)(strcase "*7-6*"))
                    (wcmatch(strcase ItemDescription)(strcase "*8-7*"))
                    (wcmatch(strcase ItemDescription)(strcase "*9-8*"))
                    (wcmatch(strcase ItemDescription)(strcase "*10-9*"))
                    (wcmatch(strcase ItemDescription)(strcase "*9-6*"))
                    (wcmatch(strcase ItemDescription)(strcase "*9-7*"))
                    (wcmatch(strcase ItemDescription)(strcase "*10-7*"))
                    (wcmatch(strcase ItemDescription)(strcase "*12-7*"))
                    (wcmatch(strcase ItemDescription)(strcase "*14-7*"))
                    (wcmatch(strcase ItemDescription)(strcase "*12-9*"))
                    (wcmatch(strcase ItemDescription)(strcase "*14-9*"))))
                 )
                 (and
                 (or(wcmatch(strcase ItemSourceFileName)(strcase "*45Deg on Rd Saddle*"))
                    (wcmatch(strcase ItemDescription)(strcase "*45 Deg Sad*"))
                    (wcmatch ItemCID "875"))
                 (not(or(wcmatch(strcase ItemDescription)(strcase "*6\" on 6\"*"))
                    (wcmatch(strcase ItemDescription)(strcase "*6 on 6*"))
                    (wcmatch(strcase ItemDescription)(strcase "*6\" on 8\"*"))
                    (wcmatch(strcase ItemDescription)(strcase "*6 on 8*"))
                    (wcmatch(strcase ItemDescription)(strcase "*6\" on 10\"*"))
                    (wcmatch(strcase ItemDescription)(strcase "*6 on 10*"))
                    (wcmatch(strcase ItemDescription)(strcase "*6\" on 12\"*"))
                    (wcmatch(strcase ItemDescription)(strcase "*6 on 12*"))
                    (wcmatch(strcase ItemDescription)(strcase "*6\" on 14\"*"))
                    (wcmatch(strcase ItemDescription)(strcase "*6 on 14*"))
                    (wcmatch(strcase ItemDescription)(strcase "*6\" on 16\"*"))
                    (wcmatch(strcase ItemDescription)(strcase "*6 on 16*"))
                    (wcmatch(strcase ItemDescription)(strcase "*6\" on 18\"*"))
                    (wcmatch(strcase ItemDescription)(strcase "*6 on 18*"))
                    (wcmatch(strcase ItemDescription)(strcase "*8\" on 8\"*"))
                    (wcmatch(strcase ItemDescription)(strcase "*8 on 8*"))
                    (wcmatch(strcase ItemDescription)(strcase "*8\" on 10\"*"))
                    (wcmatch(strcase ItemDescription)(strcase "*8 on 10*"))
                    (wcmatch(strcase ItemDescription)(strcase "*8\" on 12\"*"))
                    (wcmatch(strcase ItemDescription)(strcase "*8 on 12*"))
                    (wcmatch(strcase ItemDescription)(strcase "*8\" on 14\"*"))
                    (wcmatch(strcase ItemDescription)(strcase "*8 on 14*"))
                    (wcmatch(strcase ItemDescription)(strcase "*8\" on 16\"*"))
                    (wcmatch(strcase ItemDescription)(strcase "*8 on 16*"))
                    (wcmatch(strcase ItemDescription)(strcase "*8\" on 18\"*"))
                    (wcmatch(strcase ItemDescription)(strcase "*8 on 18*"))
                    (wcmatch(strcase ItemDescription)(strcase "*10\" on 10\"*"))
                    (wcmatch(strcase ItemDescription)(strcase "*10 on 10*"))
                    (wcmatch(strcase ItemDescription)(strcase "*10\" on 12\"*"))
                    (wcmatch(strcase ItemDescription)(strcase "*10 on 12*"))
                    (wcmatch(strcase ItemDescription)(strcase "*10\" on 14\"*"))
                    (wcmatch(strcase ItemDescription)(strcase "*10 on 14*"))
                    (wcmatch(strcase ItemDescription)(strcase "*10\" on 16\"*"))
                    (wcmatch(strcase ItemDescription)(strcase "*10 on 16*"))
                    (wcmatch(strcase ItemDescription)(strcase "*10\" on 18\"*"))
                    (wcmatch(strcase ItemDescription)(strcase "*10 on 18*"))
                    (wcmatch(strcase ItemDescription)(strcase "*10\" on 20\"*"))
                    (wcmatch(strcase ItemDescription)(strcase "*10 on 20*"))
                    (wcmatch(strcase ItemDescription)(strcase "*14\" on 14\"*"))
                    (wcmatch(strcase ItemDescription)(strcase "*14 on 14*"))
                    (wcmatch(strcase ItemDescription)(strcase "*14\" on 16\"*"))
                    (wcmatch(strcase ItemDescription)(strcase "*14 on 16*"))))
                 )
                 (and
                 (or(wcmatch(strcase ItemSourceFileName)(strcase "*45Deg Flat Saddle*"))
                    (wcmatch(strcase ItemDescription)(strcase "*45D Flat*"))
                    (wcmatch ItemCID "16"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))))
                 )
                 (and
                 (or(wcmatch(strcase ItemSourceFileName)(strcase "*Rd on Rd Conical*"))
                    (wcmatch(strcase ItemDescription)(strcase "*#8 *"))
                    (wcmatch ItemCID "751"))
                 (not(or(wcmatch(strcase ItemDescription)(strcase "*6\" on 8\"*"))
                    (wcmatch(strcase ItemDescription)(strcase "*6 on 8*"))
                    (wcmatch(strcase ItemDescription)(strcase "*6\" on 10\"*"))
                    (wcmatch(strcase ItemDescription)(strcase "*6 on 10*"))
                    (wcmatch(strcase ItemDescription)(strcase "*6\" on 12\"*"))
                    (wcmatch(strcase ItemDescription)(strcase "*6 on 12*"))
                    (wcmatch(strcase ItemDescription)(strcase "*6\" on 14\"*"))
                    (wcmatch(strcase ItemDescription)(strcase "*6 on 14*"))
                    (wcmatch(strcase ItemDescription)(strcase "*6\" on 16\"*"))
                    (wcmatch(strcase ItemDescription)(strcase "*6 on 16*"))
                    (wcmatch(strcase ItemDescription)(strcase "*6\" on 18\"*"))
                    (wcmatch(strcase ItemDescription)(strcase "*6 on 18*"))
                    (wcmatch(strcase ItemDescription)(strcase "*6\" on 20\"*"))
                    (wcmatch(strcase ItemDescription)(strcase "*6 on 20*"))
                    (wcmatch(strcase ItemDescription)(strcase "*8\" on 10\"*"))
                    (wcmatch(strcase ItemDescription)(strcase "*8 on 10*"))
                    (wcmatch(strcase ItemDescription)(strcase "*8\" on 12\"*"))
                    (wcmatch(strcase ItemDescription)(strcase "*8 on 12*"))
                    (wcmatch(strcase ItemDescription)(strcase "*8\" on 14\"*"))
                    (wcmatch(strcase ItemDescription)(strcase "*8 on 14*"))
                    (wcmatch(strcase ItemDescription)(strcase "*8\" on 16\"*"))
                    (wcmatch(strcase ItemDescription)(strcase "*8 on 16*"))
                    (wcmatch(strcase ItemDescription)(strcase "*8\" on 18\"*"))
                    (wcmatch(strcase ItemDescription)(strcase "*8 on 18*"))
                    (wcmatch(strcase ItemDescription)(strcase "*10\" on 12\"*"))
                    (wcmatch(strcase ItemDescription)(strcase "*10 on 12*"))
                    (wcmatch(strcase ItemDescription)(strcase "*10\" on 14\"*"))
                    (wcmatch(strcase ItemDescription)(strcase "*10 on 14*"))
                    (wcmatch(strcase ItemDescription)(strcase "*10\" on 16\"*"))
                    (wcmatch(strcase ItemDescription)(strcase "*10 on 16*"))
                    (wcmatch(strcase ItemDescription)(strcase "*10\" on 18\"*"))
                    (wcmatch(strcase ItemDescription)(strcase "*10 on 18*"))
                    (wcmatch(strcase ItemDescription)(strcase "*12\" on 14\"*"))
                    (wcmatch(strcase ItemDescription)(strcase "*12 on 14*"))
                    (wcmatch(strcase ItemDescription)(strcase "*12\" on 16\"*"))
                    (wcmatch(strcase ItemDescription)(strcase "*12 on 16*"))
                    (wcmatch(strcase ItemDescription)(strcase "*12\" on 18\"*"))
                    (wcmatch(strcase ItemDescription)(strcase "*12 on 18*"))
                    (wcmatch(strcase ItemDescription)(strcase "*12\" on 20\"*"))
                    (wcmatch(strcase ItemDescription)(strcase "*12 on 20*"))
                    (wcmatch(strcase ItemDescription)(strcase "*14\" on 16\"*"))
                    (wcmatch(strcase ItemDescription)(strcase "*14 on 16*"))
                    (wcmatch(strcase ItemDescription)(strcase "*14\" on 18\"*"))
                    (wcmatch(strcase ItemDescription)(strcase "*14 on 18*"))))
                 )
                 (and
                 (or(wcmatch(strcase ItemSourceFileName)(strcase "*Round Access Door*"))
                    (wcmatch(strcase ItemSourceFileName)(strcase "*#7 Access Door*")))
                 (not(or(wcmatch(strcase ItemDescription)(strcase "*6\"*"))
                    (wcmatch(strcase ItemDescription)(strcase "*8\"*"))
                    (wcmatch(strcase ItemDescription)(strcase "*10\"*"))
                    (wcmatch(strcase ItemDescription)(strcase "*12\"*"))
                    (wcmatch(strcase ItemDescription)(strcase "*14\"*"))))
                 )
                 (and
                 (or(wcmatch(strcase ItemSourceFileName)(strcase "*Conical Flat Tap*"))
                    (wcmatch(strcase ItemSourceFileName)(strcase "*Flat Conical 1\" Flg*"))
                    (wcmatch ItemCID "345"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(and(wcmatch ItemCID "51")(wcmatch(strcase ItemSourceFileName)(strcase "*6\" Start Collar wFlg*"))(wcmatch(strcase ItemDescription)(strcase "*for Damper*")))
                    (and(wcmatch ItemCID "51")(wcmatch(strcase ItemDescription)(strcase "*Damper*"))))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(and(wcmatch ItemCID "51")(wcmatch(strcase ItemSourceFileName)(strcase "*6\" Start Collar wFlg*"))(not(wcmatch(strcase ItemDescription)(strcase "*for Damper*"))))
                    (and(wcmatch ItemCID "51")(not(wcmatch(strcase ItemDescription)(strcase "*Damper*")))))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))))
                 )
                 (and
                 (or(wcmatch(strcase ItemSourceFileName)(strcase "Coupling")))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(wcmatch ItemCID "522")
                    (wcmatch(strcase ItemSourceFileName)(strcase "#2 Coupling")))
                 (not(or(= dim1 6)
                    (= dim1 7)
                    (= dim1 8)
                    (= dim1 9)
                    (= dim1 10)
                    (= dim1 12)
                    (= dim1 14)
                    (= dim1 16)
                    (= dim1 18)
                    (= dim1 20)))
                 )
                 )
                 )
                (setq Activity# "313")
                (if(and(not(or(wcmatch(strcase ItemService)(strcase "*Weld*"))(wcmatch(strcase ItemServiceType)(strcase "*Equipment*"))))
                   (or
                   (and(wcmatch(strcase ItemDescription)(strcase "Straight"))
                       (or(wcmatch(strcase c1Name)(strcase "TDF*"))
                          (wcmatch(strcase c2Name)(strcase "TDF*"))
                          (wcmatch(strcase c1Name)(strcase "*JF*"))
                          (wcmatch(strcase c2Name)(strcase "*JF*")))
                       (< ItemLengthAngle 56)
                   )
                   (and(wcmatch(strcase ItemDescription)(strcase "Straight"))
                       (or(wcmatch(strcase c1Name)(strcase "Stand S&D"))
                          (wcmatch(strcase c1Name)(strcase "Flat S&D"))
                          (wcmatch(strcase c2Name)(strcase "Stand S&D"))
                          (wcmatch(strcase c2Name)(strcase "Flat S&D"))
                          (wcmatch(strcase c1Name)(strcase "*S&D*"))
                          (wcmatch(strcase c2Name)(strcase "*S&D*")))
                       (< ItemLengthAngle 59))
                   (wcmatch(strcase ItemDescription)(strcase "Cut Joint"))
                   (wcmatch(strcase ItemDescription)(strcase "Plenum"))
                   (wcmatch(strcase ItemSourceFileName)(strcase "Transition"))
                   (wcmatch(strcase ItemSourceFileName)(strcase "*Rect Elbow"))
                   (wcmatch(strcase ItemSourceFileName)(strcase "F16"))
                   (wcmatch(strcase ItemSourceFileName)(strcase "F 16"))
                   (wcmatch(strcase ItemSourceFileName)(strcase "F17"))
                   (wcmatch(strcase ItemSourceFileName)(strcase "F41"))
                   (wcmatch(strcase ItemSourceFileName)(strcase "F2"))
                   (wcmatch(strcase ItemSourceFileName)(strcase "F4"))
                   (wcmatch(strcase ItemSourceFileName)(strcase "SQ-RD"))
                   (wcmatch(strcase ItemSourceFileName)(strcase "TDF CAP"))
                   (wcmatch(strcase ItemSourceFileName)(strcase "SD CAP"))
                   (wcmatch(strcase ItemSourceFileName)(strcase "PLUG CAP"))
                   (wcmatch(strcase ItemSourceFileName)(strcase "S&D CAP"))
                   ))
                  (setq Activity# "317")
                (if(wcmatch(strcase ItemService)(strcase "*Weld*"))
                  (setq Activity# "318")
                  (setq Activity# "Unassigned")
  ) ) ) ) ) ) ) ) ) ) );end ifs
      (vlax-put-property vla "CustomData" (strcat "ItemCID" " = " ItemCID ","))
      (vlax-put-property vla "CustomData" (strcat "Activity_#" " = " Activity# ","))
        (setq i (1+ i))
      );end while
  (UpdateJobData 10 jobName)
  (UpdateJobData 11 job#)
  (terpri)(princ "-- Activity Numbers and ItemCIDs Updated")(princ)
  (princ)
      );end progn
    (progn(terpri)(princ "-- Activity Number and ItemCID Update Skipped (Only Version 2019 or Later) --")(princ))
    );end if
  );end progn
  (terpri)(princ "Updating Layer Colors --")(princ)
  (c:Fix_Colors)
  (terpri)(princ "-- Layer Colors Updated")(princ)
  (if(not(= writeToVBCode nil))(progn(close writeToVBCode)(setq writeToVBCode nil)))
  (if(not(= vbcode nil))(progn(vl-file-delete vbCode)(setq vbcode nil)))
  (if(not(= doc nil))(vla-endundomark doc))
  (terpri)(princ "-- Update Complete")(princ)
  ;(command-s "._qsave" (if(> (getvar 'cmdactive) 0) "")(if(> (getvar 'cmdactive) 0) "N"))
  (princ)
(END_ROUTINE));end defun
;**************************************************************************************************************************************************
(defun c:Adjust_Dampers ()
;;;; KS7L = Switch Damper to KS7L
  (OUTSIDE_LOOP_VARIABLES nil)
  (setq sset (ssget '((0 . "MAPS_SOLID"))))
  (initget 0 "C T 2 3 4 23 24 34 234 _ClearAll,C TapsOnly,T 2Trunk(D2),2 3Branch(D3),3 4Branch(D4),4 23(D2&D3),23 24(D2&D4),24 34(D3&D4),34 234(D2&D3&D4),234")
  (setq choice (getkword "\nEnter desired damper location(s): [Clear all/Tap Dampers/(2) Trunk D2/(3) Left Branch D3/(4) Right Branch D4/(23) D2 & D3/(24) D2 & D4/(34) D3 & D4/(234) D2 & D3 & D4] <Esc>")
        3/8thsRod "\"3/8\"+qt+\" ROD-L\""
        KS7L "\"KS7L-DN\""
        i 0);end setq
    (if(wcmatch choice "*TapsOnly*")
      (progn
        (write-line "requires task.selection" writeToVBCode)
        (write-line "dim i = 1" writeToVBCode)
        (write-line "dim qt = ASCII(34)" writeToVBCode)
        (write-line "while i <= task.selection.count" writeToVBCode)
        (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
        (write-line "i = i + 1" writeToVBCode)
        (write-line "end while" writeToVBCode)
        (close writeToVBCode)
        (Executescript vbCode sset)
        (vl-file-delete vbCode)
        (prompt "Added Tap dampers.")(princ)
        (princ)
      );progn
    (if(and(wcmatch choice "*Trunk*")(wcmatch choice "2*"))
      (progn
        (write-line "requires task.selection" writeToVBCode)
        (write-line "dim i = 1" writeToVBCode)
        (write-line "dim qt = ASCII(34)" writeToVBCode)
        (write-line "while i <= task.selection.count" writeToVBCode)
        (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
        (write-line "if item.dampers > 0 and item.dampers < 5 then" writeToVBCode)
        (write-line "if item.filename = \"Wye\" or item.filename = \"Lateral 45\" or item.filename = \"Conical Cross\" then" writeToVBCode)
        (write-line "if item.dim[\"D2 Trunk Diameter\"].value > 12 then" writeToVBCode)
        (write-line "item.damper[2].value = \"3/8\"+qt+\" ROD-D2\"" writeToVBCode)
        (write-line "item.damper[2].locked = true" writeToVBCode)
        (write-line "item.dim[\"D2 DAMPER COLLAR\"].value = 6" writeToVBCode)
        (write-line "elseif item.dim[\"D2 Trunk Diameter\"].value < 13 then" writeToVBCode)
        (write-line "item.damper[2].value = \"KS7L-D2\"" writeToVBCode)
        (write-line "item.damper[2].locked = true" writeToVBCode)
        (write-line "item.dim[\"D2 DAMPER COLLAR\"].value = 6" writeToVBCode)
        (write-line "item.update()" writeToVBCode)
        (write-line "end if" writeToVBCode)
        (write-line "end if" writeToVBCode)
        (write-line "end if" writeToVBCode)
        (write-line "i = i + 1" writeToVBCode)
        (write-line "end while" writeToVBCode)
        (close writeToVBCode)
        (Executescript vbCode sset)
        (vl-file-delete vbCode)
        (prompt "Added Trunk dampers to item(s).")(princ)
        (princ)
      );progn
      (if(and(wcmatch choice "*Branch*")(wcmatch choice "4*"))
        (progn
          (write-line "requires task.selection" writeToVBCode)
          (write-line "dim i = 1" writeToVBCode)
          (write-line "dim qt = ASCII(34)" writeToVBCode)
          (write-line "while i <= task.selection.count" writeToVBCode)
          (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
          (write-line "if item.dampers > 3 and item.dampers < 5 then" writeToVBCode)
          (write-line "if item.filename = \"Wye\" or item.filename = \"Lateral 45\" or item.filename = \"Conical Cross\" then" writeToVBCode)
          (write-line "if item.dim[\"D4 Right Branch Diameter\"].value > 12 then" writeToVBCode)
          (write-line "item.damper[4].value = \"3/8\"+qt+\" ROD-DN\"" writeToVBCode)
          (write-line "item.damper[4].locked = true" writeToVBCode)
          (write-line "item.update()" writeToVBCode)
          (write-line "elseif item.dim[\"D4 Right Branch Diameter\"].value < 13 then" writeToVBCode)
          (write-line "item.damper[4].value = \"KS7L-DN\"" writeToVBCode)
          (write-line "item.damper[4].locked = true" writeToVBCode)
          (write-line "item.update()" writeToVBCode)
          (write-line "end if" writeToVBCode)
          (write-line "if item.damper[2].value <> \"None\" then" writeToVBCode)
          (write-line "item.dim[\"D2 DAMPER COLLAR\"].value = 6" writeToVBCode)
          (write-line "item.update()" writeToVBCode)
          (write-line "end if" writeToVBCode)
          (write-line "end if" writeToVBCode)
          (write-line "end if" writeToVBCode)
          (write-line "i = i + 1" writeToVBCode)
          (write-line "end while" writeToVBCode)
          (close writeToVBCode)
          (Executescript vbCode sset)
          (vl-file-delete vbCode)
          (prompt "Added Right dampers to item(s).")(princ)
          (princ)
        );progn
        (if(and(wcmatch choice "*Branch*")(wcmatch choice "3*"))
          (progn
            (write-line "requires task.selection" writeToVBCode)
            (write-line "dim i = 1" writeToVBCode)
            (write-line "dim qt = ASCII(34)" writeToVBCode)
            (write-line "while i <= task.selection.count" writeToVBCode)
            (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
            (write-line "if item.dampers > 2 and item.dampers < 5 then" writeToVBCode)
            (write-line "if item.filename = \"Wye\" or item.filename = \"Lateral 45\" or item.filename = \"Conical Cross\" then" writeToVBCode)
            (write-line "if item.dim[\"D3 Left Branch Diameter\"].value > 12 then" writeToVBCode)
            (write-line "item.damper[3].value = \"3/8\"+qt+\" ROD-DN\"" writeToVBCode)
            (write-line "item.damper[3].locked = true" writeToVBCode)
            (write-line "item.update()" writeToVBCode)
            (write-line "elseif item.dim[\"D3 Left Branch Diameter\"].value < 13 then" writeToVBCode)
            (write-line "item.damper[3].value = \"KS7L-DN\"" writeToVBCode)
            (write-line "item.damper[3].locked = true" writeToVBCode)
            (write-line "item.update()" writeToVBCode)
            (write-line "end if" writeToVBCode)
            (write-line "if item.damper[2].value <> \"None\" then" writeToVBCode)
            (write-line "item.dim[\"D2 DAMPER COLLAR\"].value = 6" writeToVBCode)
            (write-line "item.update()" writeToVBCode)
            (write-line "end if" writeToVBCode)
            (write-line "end if" writeToVBCode)
            (write-line "end if" writeToVBCode)
            (write-line "i = i + 1" writeToVBCode)
            (write-line "end while" writeToVBCode)
            (close writeToVBCode)
            (Executescript vbCode sset)
            (vl-file-delete vbCode)
            (prompt "Added Left dampers to item(s).")(princ)
            (princ)
          );progn
          (if(wcmatch choice "Clear*")
            (progn
              (write-line "requires task.selection" writeToVBCode)
              (write-line "dim i = 1" writeToVBCode)
              (write-line "dim qt = ASCII(34)" writeToVBCode)
              (write-line "while i <= task.selection.count" writeToVBCode)
              (write-line "dim item = task.selection[i]" writeToVBCode)
        (write-line "if item.filename = \"Rd on Rd Conical 1'' Flg (for Damper)\" then" writeToVBCode)
        (write-line "item.damper[2].value = \"None\"" writeToVBCode)
        (write-line "item.damper[2].locked = true" writeToVBCode)
        (write-line "item.update()" writeToVBCode)
        (write-line "elseif item.filename = \"6'' Start Collar wFlg (for Damper)\" then" writeToVBCode)
        (write-line "item.damper[2].value = \"None\"" writeToVBCode)
        (write-line "item.damper[2].locked = true" writeToVBCode)
        (write-line "item.update()" writeToVBCode)
        (write-line "elseif item.filename = \"45Deg on Rd Saddle\" or item.filename = \"Rd on Rd Straight 1'' Flg\" then" writeToVBCode) 
        (write-line "item.damper[2].value = \"None\"" writeToVBCode)
        (write-line "item.damper[2].locked = true" writeToVBCode)
        (write-line "item.update()" writeToVBCode)
        (write-line "elseif item.filename = \"Flat Conical 1'' Flg (for Damper)\" or item.filename = \"45Deg Flat Saddle\" then" writeToVBCode)
        (write-line "item.damper[1].value = \"None\"" writeToVBCode)
        (write-line "item.damper[1].locked = true" writeToVBCode)
        (write-line "end if" writeToVBCode)
        (write-line "item.update()" writeToVBCode)
              (write-line "if item.dampers > 0 and item.dampers < 5 then" writeToVBCode)
              (write-line "if item.filename = \"Wye\" or item.filename = \"Lateral 45\" or item.filename = \"Conical Cross\" then" writeToVBCode)
              (write-line "item.damper[2].value = \"None\"" writeToVBCode)
              (write-line "item.damper[2].locked = true" writeToVBCode)
              (write-line "item.dim[\"D2 DAMPER COLLAR\"].value = 0" writeToVBCode)
              (write-line "item.update()" writeToVBCode)
              (write-line "item.damper[3].value = \"None\"" writeToVBCode)
              (write-line "item.damper[3].locked = true" writeToVBCode)
              (write-line "item.update()" writeToVBCode)
              (write-line "item.damper[4].value = \"None\"" writeToVBCode)
              (write-line "item.damper[4].locked = true" writeToVBCode)
              (write-line "item.update()" writeToVBCode)
              (write-line "end if" writeToVBCode)
              (write-line "end if" writeToVBCode)
              (write-line "i = i + 1" writeToVBCode)
              (write-line "end while" writeToVBCode)
              (close writeToVBCode)
              (Executescript vbCode sset)
              (vl-file-delete vbCode)
              (prompt "Cleared all (D2,D3,D4) dampers from item(s).")(princ)
              (princ)
            );progn
            (if(wcmatch choice "24(*")
              (progn
                (write-line "requires task.selection" writeToVBCode)
                (write-line "dim i = 1" writeToVBCode)
                (write-line "dim qt = ASCII(34)" writeToVBCode)
                (write-line "while i <= task.selection.count" writeToVBCode)
                (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                (write-line "if item.dampers > 3 and item.dampers < 5 then" writeToVBCode)
                (write-line "if item.filename = \"Wye\" or item.filename = \"Lateral 45\" or item.filename = \"Conical Cross\" then" writeToVBCode)
                (write-line "if item.dim[\"D2 Trunk Diameter\"].value > 12 then" writeToVBCode)
                (write-line "item.damper[2].value = \"3/8\"+qt+\" ROD-D2\"" writeToVBCode)
                (write-line "item.damper[2].locked = true" writeToVBCode)
                (write-line "item.dim[\"D2 DAMPER COLLAR\"].value = 6" writeToVBCode)
                (write-line "item.update()" writeToVBCode)
                (write-line "elseif item.dim[\"D2 Trunk Diameter\"].value < 13 then" writeToVBCode)
                (write-line "item.damper[2].value = \"KS7L-D2\"" writeToVBCode)
                (write-line "item.damper[2].locked = true" writeToVBCode)
                (write-line "item.dim[\"D2 DAMPER COLLAR\"].value = 6" writeToVBCode)
                (write-line "item.update()" writeToVBCode)
                (write-line "end if" writeToVBCode)
                (write-line "if item.dim[\"D4 Right Branch Diameter\"].value > 12 then" writeToVBCode)
                (write-line "item.damper[4].value = \"3/8\"+qt+\" ROD-DN\"" writeToVBCode)
                (write-line "item.damper[4].locked = true" writeToVBCode)
                (write-line "item.update()" writeToVBCode)
                (write-line "elseif item.dim[\"D4 Right Branch Diameter\"].value < 13 then" writeToVBCode)
                (write-line "item.damper[4].value = \"KS7L-DN\"" writeToVBCode)
                (write-line "item.damper[4].locked = true" writeToVBCode)
                (write-line "item.update()" writeToVBCode)
                (write-line "end if" writeToVBCode)
                (write-line "end if" writeToVBCode)
                (write-line "end if" writeToVBCode)
                (write-line "i = i + 1" writeToVBCode)
                (write-line "end while" writeToVBCode)
                (close writeToVBCode)
                (Executescript vbCode sset)
                (vl-file-delete vbCode)
                (prompt "Added Trunk and Right dampers to item(s).")(princ)
                (princ)
              );progn
              (if(wcmatch choice "23(*")
                (progn
                  (write-line "requires task.selection" writeToVBCode)
                  (write-line "dim i = 1" writeToVBCode)
                  (write-line "dim qt = ASCII(34)" writeToVBCode)
                  (write-line "while i <= task.selection.count" writeToVBCode)
                  (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                  (write-line "if item.dampers > 2 and item.dampers < 5 then" writeToVBCode)
                  (write-line "if item.filename = \"Wye\" or item.filename = \"Lateral 45\" or item.filename = \"Conical Cross\" then" writeToVBCode)
                  (write-line "if item.dim[\"D2 Trunk Diameter\"].value > 12 then" writeToVBCode)
                  (write-line "item.damper[2].value = \"3/8\"+qt+\" ROD-D2\"" writeToVBCode)
                  (write-line "item.damper[2].locked = true" writeToVBCode)
                  (write-line "item.dim[\"D2 DAMPER COLLAR\"].value = 6" writeToVBCode)
                  (write-line "item.update()" writeToVBCode)
                  (write-line "elseif item.dim[\"D2 Trunk Diameter\"].value < 13 then" writeToVBCode)
                  (write-line "item.damper[2].value = \"KS7L-D2\"" writeToVBCode)
                  (write-line "item.damper[2].locked = true" writeToVBCode)
                  (write-line "item.dim[\"D2 DAMPER COLLAR\"].value = 6" writeToVBCode)
                  (write-line "item.update()" writeToVBCode)
                  (write-line "end if" writeToVBCode)
                  (write-line "if item.dim[\"D3 Left Branch Diameter\"].value > 12 then" writeToVBCode)
                  (write-line "item.damper[3].value = \"3/8\"+qt+\" ROD-DN\"" writeToVBCode)
                  (write-line "item.damper[3].locked = true" writeToVBCode)
                  (write-line "item.update()" writeToVBCode)
                  (write-line "elseif item.dim[\"D3 Left Branch Diameter\"].value < 13 then" writeToVBCode)
                  (write-line "item.damper[3].value = \"KS7L-DN\"" writeToVBCode)
                  (write-line "item.damper[3].locked = true" writeToVBCode)
                  (write-line "item.update()" writeToVBCode)
                  (write-line "end if" writeToVBCode)
                  (write-line "end if" writeToVBCode)
                  (write-line "end if" writeToVBCode)
                  (write-line "i = i + 1" writeToVBCode)
                  (write-line "end while" writeToVBCode)
                  (close writeToVBCode)
                  (Executescript vbCode sset)
                  (vl-file-delete vbCode)
                  (prompt "Added Trunk and Left dampers to item(s).")(princ)
                  (princ)
                );progn
                (if(wcmatch choice "234(*")
                  (progn
                    (write-line "requires task.selection" writeToVBCode)
                    (write-line "dim i = 1" writeToVBCode)
                    (write-line "dim qt = ASCII(34)" writeToVBCode)
                    (write-line "while i <= task.selection.count" writeToVBCode)
                    (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                    (write-line "if item.dampers > 3 and item.dampers < 5 then" writeToVBCode)
                    (write-line "if item.filename = \"Wye\" or item.filename = \"Lateral 45\" or item.filename = \"Conical Cross\" then" writeToVBCode)
                    (write-line "if item.dim[\"D2 Trunk Diameter\"].value > 12 then" writeToVBCode)
                    (write-line "item.damper[2].value = \"3/8\"+qt+\" ROD-D2\"" writeToVBCode)
                    (write-line "item.damper[2].locked = true" writeToVBCode)
                    (write-line "item.dim[\"D2 DAMPER COLLAR\"].value = 6" writeToVBCode)
                    (write-line "item.update()" writeToVBCode)
                    (write-line "elseif item.dim[\"D2 Trunk Diameter\"].value < 13 then" writeToVBCode)
                    (write-line "item.damper[2].value = \"KS7L-D2\"" writeToVBCode)
                    (write-line "item.damper[2].locked = true" writeToVBCode)
                    (write-line "item.dim[\"D2 DAMPER COLLAR\"].value = 6" writeToVBCode)
                    (write-line "item.update()" writeToVBCode)
                    (write-line "end if" writeToVBCode)
                    (write-line "if item.dim[\"D3 Left Branch Diameter\"].value > 12 then" writeToVBCode)
                    (write-line "item.damper[3].value = \"3/8\"+qt+\" ROD-DN\"" writeToVBCode)
                    (write-line "item.damper[3].locked = true" writeToVBCode)
                    (write-line "item.update()" writeToVBCode)
                    (write-line "elseif item.dim[\"D3 Left Branch Diameter\"].value < 13 then" writeToVBCode)
                    (write-line "item.damper[3].value = \"KS7L-DN\"" writeToVBCode)
                    (write-line "item.damper[3].locked = true" writeToVBCode)
                    (write-line "item.update()" writeToVBCode)
                    (write-line "end if" writeToVBCode)
                    (write-line "if item.dim[\"D4 Right Branch Diameter\"].value > 12 then" writeToVBCode)
                    (write-line "item.damper[4].value = \"3/8\"+qt+\" ROD-DN\"" writeToVBCode)
                    (write-line "item.damper[4].locked = true" writeToVBCode)
                    (write-line "item.update()" writeToVBCode)
                    (write-line "elseif item.dim[\"D4 Right Branch Diameter\"].value < 13 then" writeToVBCode)
                    (write-line "item.damper[4].value = \"KS7L-DN\"" writeToVBCode)
                    (write-line "item.damper[4].locked = true" writeToVBCode)
                    (write-line "item.update()" writeToVBCode)
                    (write-line "end if" writeToVBCode)
                    (write-line "end if" writeToVBCode)
                    (write-line "end if" writeToVBCode)
                    (write-line "i = i + 1" writeToVBCode)
                    (write-line "end while" writeToVBCode)
                    (close writeToVBCode)
                    (Executescript vbCode sset)
                    (vl-file-delete vbCode)
                    (prompt "Added all (D2,D3,D4) dampers to item(s).")(princ)
                    (princ)
                  );progn
                  (if(wcmatch choice "34(*")
                    (progn
                      (write-line "requires task.selection" writeToVBCode)
                      (write-line "dim i = 1" writeToVBCode)
                      (write-line "dim qt = ASCII(34)" writeToVBCode)
                      (write-line "while i <= task.selection.count" writeToVBCode)
                      (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                      (write-line "if item.dampers > 3 and item.dampers < 5 then" writeToVBCode)
                      (write-line "if item.filename = \"Wye\" or item.filename = \"Lateral 45\" or item.filename = \"Conical Cross\" then" writeToVBCode)
                      (write-line "if item.dim[\"D3 Left Branch Diameter\"].value > 12 then" writeToVBCode)
                      (write-line "item.damper[3].value = \"3/8\"+qt+\" ROD-DN\"" writeToVBCode)
                      (write-line "item.damper[3].locked = true" writeToVBCode)
                      (write-line "item.update()" writeToVBCode)
                      (write-line "elseif item.dim[\"D3 Left Branch Diameter\"].value < 13 then" writeToVBCode)
                      (write-line "item.damper[3].value = \"KS7L-DN\"" writeToVBCode)
                      (write-line "item.damper[3].locked = true" writeToVBCode)
                      (write-line "item.update()" writeToVBCode)
                      (write-line "end if" writeToVBCode)
                      (write-line "if item.dim[\"D4 Right Branch Diameter\"].value > 12 then" writeToVBCode)
                      (write-line "item.damper[4].value = \"3/8\"+qt+\" ROD-DN\"" writeToVBCode)
                      (write-line "item.damper[4].locked = true" writeToVBCode)
                      (write-line "item.update()" writeToVBCode)
                      (write-line "elseif item.dim[\"D4 Right Branch Diameter\"].value < 13 then" writeToVBCode)
                      (write-line "item.damper[4].value = \"KS7L-DN\"" writeToVBCode)
                      (write-line "item.damper[4].locked = true" writeToVBCode)
                      (write-line "item.update()" writeToVBCode)
                      (write-line "end if" writeToVBCode)
                      (write-line "if item.damper[2].value <> \"None\" then" writeToVBCode)
                      (write-line "item.dim[\"D2 DAMPER COLLAR\"].value = 6" writeToVBCode)
                      (write-line "item.update()" writeToVBCode)
                      (write-line "end if" writeToVBCode)
                      (write-line "end if" writeToVBCode)
                      (write-line "end if" writeToVBCode)
                      (write-line "i = i + 1" writeToVBCode)
                      (write-line "end while" writeToVBCode)
                      (close writeToVBCode)
                      (Executescript vbCode sset)
                      (vl-file-delete vbCode)
                      (prompt "Added branch (D3,D4) dampers to item(s).")(princ)
                      (princ)
                    );progn
    ) ) ) ) ) ) ) ) )
(END_ROUTINE));end defun
;**************************************************************************************************************************************************
(defun c:Item_Update ()
  (setq i 0
        sset (ssget '((0 . "MAPS_SOLID"))));end setq
  (if(not(= sset nil))
    (progn
      (OUTSIDE_LOOP_VARIABLES nil)
      (write-line "requires task.selection" writeToVBCode)
      (write-line "dim i = 1" writeToVBCode)
      (write-line "dim qt = ASCII(34)" writeToVBCode)
      (write-line "while i <= task.selection.count" writeToVBCode)
      (write-line "dim item = task.selection[i]" writeToVBCode)
      (write-line "item.update()" writeToVBCode)
      (write-line "i = i + 1" writeToVBCode)
      (write-line "end while" writeToVBCode)
      (close writeToVBCode)
      (Executescript vbCode sset)
      (vl-file-delete vbCode)
    );progn
  );end if
  (princ)
(END_ROUTINE));end defun
;**************************************************************************************************************************************************
(defun c:Multi_Variable_Edit ()
  (OUTSIDE_LOOP_VARIABLES nil)
  (print "Please select your desired items:")(princ)(terpri)
  (setq i 0
        index nil
        operator nil
        parameterChoice nil
        valueChoice nil
        parameter nil
        dimIndexPara nil
        optionIndexPara nil
        valueChoice nil
        operator nil
        twoVariables nil
        stringValue1 nil
        stringValue2 nil
        dimIndexValue1 nil
        indexValue1 nil
        valueParameter1 nil
        value1Type nil
        optionIndexValue1 nil
        providedNumber1 nil
        stringValue2 nil
        dimIndexValue2 nil
        indexValue2 nil
        valueParameter2 nil
        value2Type nil
        optionIndexValue2 nil
        providedNumber2 nil
        dimIndexValue nil
        indexValue nil
        valueParameter nil
        valueType nil
        providedNumber nil
        dimIndexList nil
        optionIndexList nil
        dimCompare nil
        optionCompare nil
        dimElement nil
        dimComparison nil
        optionElement nil
        optionComparison nil
        adjustedValue nil
        validityCheck nil
        variableValue nil
        variableValue1 nil
        variableValue2 nil
        decisionLine nil
        sset (ssget '((0 . "MAPS_SOLID"))))
  (print "Always include D for Dimension or O for option (absence assumes Dimension is desired).")(princ)(terpri)
  (print "Index locations can be used; IE: D3 or O12.")(princ)(terpri)
  (print "Use quotation marks around dimension/option names; IE: D\"This is my dimension's name\" or O\"This is my option's name\".")(princ)(terpri)
  (setq parameterChoice (getstring "\nEnter parameter \"name\" or index# to be adjusted: [D*/O*]" T))
  (print "Direct values or equations can be applied; Special variables available: Calc,Dependent,Auto,Self,+,-,*,/")(princ)(terpri)
  (print "Examples of direct values: 123,D6,D1,O11,O3,Calc,Dependent,Auto")(princ)(terpri)
  (print "Examples of equations: 3+33,D6*D1,D3/O14,D3+D4,D4-D3,Self+Self,Self+33,Self+D4")(princ)(terpri)
  (setq valueChoice (getstring "\nEnter desired value or equation:" T))
    (if(or(wcmatch parameterChoice "D*")(wcmatch parameterChoice "d*"))
      (progn
        (if(wcmatch parameterChoice "D*")(STRING_SPLIT "D" parameterChoice)(STRING_SPLIT "d" parameterChoice))
        (setq parameter "dim"
              dimIndexPara nth0
              index nth0)
      );end progn
      (if(or(wcmatch parameterChoice "O*")(wcmatch parameterChoice "o*"))
        (progn
          (if(wcmatch parameterChoice "O*")(STRING_SPLIT "O" parameterChoice)(STRING_SPLIT "o" parameterChoice))
          (setq parameter "option"
                optionIndexPara nth0
                index nth0)
        );end progn
        (setq parameter "dim"
              index parameterChoice)
    ) );end ifs
    (if(wcmatch valueChoice "*[+]*")
      (setq operator "+"
            twoVariables T)
      (if(wcmatch valueChoice "*[-]*")
        (setq operator "-"
              twoVariables T)
        (if(wcmatch valueChoice "*[*]*")
          (setq operator "*"
                twoVariables T)
          (if(wcmatch valueChoice "*[/]*")
            (setq operator "/"
                  twoVariables T)
            (setq twoVariables nil)
    ) ) ) );end ifs
    (if twoVariables
      (progn
        (STRING_SPLIT operator valueChoice)
        (setq stringValue1 nth0
              stringValue2 nth1)
        (if(or(wcmatch stringValue1 "D*")(wcmatch stringValue1 "d*"))
          (progn(if(wcmatch stringValue1 "D*")(STRING_SPLIT "D" stringValue1)(STRING_SPLIT "d" stringValue1))
          (setq dimIndexValue1 nth0
                indexValue1 nth0
                valueParameter1 "dim"
                value1Type "Dimension"))
          (if(or(wcmatch stringValue1 "O*")(wcmatch stringValue1 "o*"))
            (progn(if(wcmatch stringValue1 "O*")(STRING_SPLIT "O" stringValue1)(STRING_SPLIT "o" stringValue1))
            (setq optionIndexValue1 nth0
                  indexValue1 nth0
                  valueParameter1 "option"
                  value1Type "Option"))
            (if(not(wcmatch stringValue1 "*@*"))
              (setq providedNumber1 stringValue1
                    value1Type "NumberValue")
              (if(or(wcmatch stringValue1 "*D*[\"]*")(wcmatch stringValue1 "*d*[\"]*"))
                (progn(STRING_SPLIT "\"" stringValue1)
                (setq indexValue1 nth1
                      valueParameter1 "dim"
                      valueType "DimensionName"))
                (if(or(wcmatch stringValue1 "*O*[\"]*")(wcmatch stringValue1 "*o*[\"]*"))
                  (progn(STRING_SPLIT "\"" stringValue1)
                  (setq indexValue1 nth1
                        valueParameter1 "option"
                        valueType "DimensionName"))
                  (if(wcmatch stringValue1 "*[\"]*")
                    (progn(STRING_SPLIT "\"" stringValue1)
                    (setq indexValue1 nth0
                          valueParameter1 "dim"
                          valueType "DimensionName"))
                    (if(or(wcmatch stringValue1 "*self*")(wcmatch stringValue1 "*Self*")(wcmatch stringValue1 "*SELF*"))
                      (setq indexValue1 index
                            valueParameter1 parameter
                            valueType "Self")
        ) ) ) ) ) ) );end ifs
        (if(or(wcmatch stringValue2 "D*")(wcmatch stringValue2 "d*"))
          (progn(if(wcmatch stringValue2 "D*")(STRING_SPLIT "D" stringValue2)(STRING_SPLIT "d" stringValue2))
          (setq dimIndexValue2 nth0
                indexValue2 nth0
                valueParameter2 "dim"
                value2Type "Dimension"))
          (if(or(wcmatch stringValue2 "O*")(wcmatch stringValue2 "o*"))
            (progn(if(wcmatch stringValue2 "O*")(STRING_SPLIT "O" stringValue2)(STRING_SPLIT "o" stringValue2))
            (setq optionIndexValue2 nth0
                  indexValue2 nth0
                  valueParameter2 "option"
                  value2Type "Option"))
            (if(not(wcmatch stringValue2 "*@*"))
              (setq providedNumber2 stringValue2
                    value2Type "NumberValue")
              (if(or(wcmatch stringValue2 "*D*[\"]*")(wcmatch stringValue2 "*d*[\"]*"))
                (progn(STRING_SPLIT "\"" stringValue2)
                (setq indexValue2 nth1
                      valueParameter2 "dim"
                      valueType "DimensionName"))
                (if(or(wcmatch stringValue2 "*O*[\"]*")(wcmatch stringValue2 "*o*[\"]*"))
                  (progn(STRING_SPLIT "\"" stringValue2)
                  (setq indexValue2 nth1
                        valueParameter2 "option"
                        valueType "DimensionName"))
                  (if(wcmatch stringValue2 "*[\"]*")
                    (progn(STRING_SPLIT "\"" stringValue2)
                    (setq indexValue2 nth0
                          valueParameter2 "dim"
                          valueType "DimensionName"))
                    (if(or(wcmatch stringValue2 "*self*")(wcmatch stringValue2 "*Self*")(wcmatch stringValue2 "*SELF*"))
                      (setq indexValue2 index
                            valueParameter2 parameter
                            valueType "Self")
        ) ) ) ) ) ) );end ifs
      );end progn
      (progn;or else condition for single value
        (if(or(wcmatch valueChoice "D*")(wcmatch valueChoice "d*"))
          (progn(if(wcmatch valueChoice "D*")(STRING_SPLIT "D" valueChoice)(STRING_SPLIT "d" valueChoice))
          (setq dimIndexValue nth0
                indexValue nth0
                valueParameter "dim"
                valueType "Dimension"))
          (if(or(wcmatch valueChoice "O*")(wcmatch valueChoice "o*"))
            (progn(if(wcmatch valueChoice "O*")(STRING_SPLIT "O" valueChoice)(STRING_SPLIT "o" valueChoice))
            (setq optionIndexValue nth0
                  indexValue nth0
                  valueParameter "option"
                  valueType "Option"))
            (if(or(wcmatch valueChoice "*calc*")(wcmatch valueChoice "*Calc*")(wcmatch valueChoice "*CALC*"))
              (setq providedNumber "1100001"
                    valueType "Calc")
              (if(or(wcmatch valueChoice "*dependent*")(wcmatch valueChoice "*Dependent*")(wcmatch valueChoice "*DEPENDENT*"))
                (setq providedNumber "1100000"
                      valueType "Dependent")
                (if(or(wcmatch valueChoice "*auto*")(wcmatch valueChoice "*Auto*")(wcmatch valueChoice "*AUTO*"))
                  (setq providedNumber "1000000"
                        valueType "Auto")
                  (if(not(wcmatch valueChoice "*@*"))
                    (setq providedNumber valueChoice
                          valueType "NumberValue")
                    (if(or(wcmatch valueChoice "*D*[\"]*")(wcmatch valueChoice "*d*[\"]*"))
                      (progn(STRING_SPLIT "\"" valueChoice)
                      (setq indexValue nth1
                            valueParameter "dim"
                            valueType "DimensionName"))
                      (if(or(wcmatch valueChoice "*O*[\"]*")(wcmatch valueChoice "*o*[\"]*"))
                        (progn(STRING_SPLIT "\"" valueChoice)
                        (setq indexValue nth1
                              valueParameter "option"
                              valueType "DimensionName"))
                        (if(wcmatch valueChoice "*[\"]*")
                          (progn(STRING_SPLIT "\"" valueChoice)
                          (setq indexValue nth0
                                valueParameter "dim"
                                valueType "DimensionName"))
                          (if(or(wcmatch valueChoice "*self*")(wcmatch valueChoice "*Self*")(wcmatch valueChoice "*SELF*"))
                            (setq indexValue index
                                  valueParameter parameter
                                  valueType "Self")
       ) ) ) ) ) ) ) ) ) );end ifs
      );end progn
    );end if
    (if(and(not(= valueType "DimensionName"))(not(= value1Type "DimensionName"))(not(= value2Type "DimensionName")))
      (progn
        (setq dimIndexList (list dimIndexPara dimIndexValue dimIndexValue1 dimIndexValue2)
              optionIndexList (list optionIndexPara optionIndexValue optionIndexValue1 optionIndexValue2)
              dimCompare 1
              optionCompare 1)
        (foreach elm dimIndexlist
          (if(and(not(=(type elm) 'INT))(not(= elm ""))(not(= elm nil)))(setq dimElement (atoi elm)))
          (if(and(not(=(type dimComparison) 'INT))(not(= dimComparison ""))(not(= dimComparison nil)))(setq dimComparison (atoi dimComparison)))
          (if(> dimElement dimComparison)(setq dimCompare dimElement))
        );end foreach
        (foreach elm optionIndexList
          (if(and(not(=(type elm) 'INT))(not(= elm ""))(not(= elm nil)))(setq optionElement (atoi elm)))
          (if(and(not(=(type optionComparison) 'INT))(not(= optionComparison ""))(not(= optionComparison nil)))(setq optionComparison (atoi optionComparison)))
          (if(> optionElement optionComparison)(setq optionCompare optionElement))
        );end foreach
      );progn
    );end if
    (setq adjustedValue (strcat "item." parameter "[" index "].value")
          validityCheck (strcat "if " (rtos dimCompare 2 0) " <= item.dims and " (rtos optionCompare 2 0) " <= item.options then"))
    (if(and(not twoVariables)(not(= valueType "Calc"))(not(= valueType "Dependent"))(not(= valueType "Auto"))(not(= valueType "NumberValue")))
      (setq variableValue (strcat "item." valueParameter "[" indexValue "].numvalue")))
    (if(and twoVariables (not(= valueType "Calc"))(not(= valueType "Dependent"))(not(= valueType "Auto"))(not(= valueType "NumberValue")))
      (setq variableValue1 (strcat "item." valueParameter1 "[" indexValue1 "].numvalue")
            variableValue2 (strcat "item." valueParameter2 "[" indexValue2 "].numvalue")))
    (if(and(< dimCompare dimensionListCount) twoVariables (not(= value1Type "Calc"))(not(= value1Type "Dependent"))(not(= value1Type "Auto"))(not(= value1Type "NumberValue"))(not(= value2Type "Calc"))(not(= value2Type "Dependent"))(not(= value2Type "Auto"))(not(= value2Type "NumberValue")))
        (setq decisionLine (strcat adjustedValue " = " variableValue1 " " operator " "  variableValue2))
      (if(and(< dimCompare dimensionListCount)(not twoVariables)(not(= valueType "Calc"))(not(= valueType "Dependent"))(not(= valueType "Auto"))(not(= valueType "NumberValue")))
          (setq decisionLine (strcat adjustedValue " = " variableValue))
        (if(and(< dimCompare dimensionListCount) twoVariables (= value1Type "NumberValue")(= value2Type "NumberValue"))
            (setq decisionLine (strcat adjustedValue " = " providedNumber1 " " operator " " providedNumber2))
          (if(and(< dimCompare dimensionListCount)(not twoVariables)(or(= valueType "Calc")(= valueType "Dependent")(= valueType "Auto")(= valueType "NumberValue")))
              (setq decisionLine (strcat adjustedValue " = " providedNumber))
            (if(and(< dimCompare dimensionListCount) twoVariables (not(= value1Type "Calc"))(not(= value1Type "Dependent"))(not(= value1Type "Auto"))(not(= value1Type "NumberValue"))(= value2Type "NumberValue"))
                (setq decisionLine (strcat adjustedValue " = " variableValue1 " " operator " " providedNumber2))
              (if(and(< dimCompare dimensionListCount) twoVariables (= value1Type "NumberValue")(not(= value2Type "Calc"))(not(= value2Type "Dependent"))(not(= value2Type "Auto"))(not(= value2Type "NumberValue")))
                  (setq decisionLine (strcat adjustedValue " = " providedNumber1 " " operator " " variableValue2))
    ) ) ) ) ) );end ifs
  (write-line "requires task.selection" writeToVBCode)
  (write-line "dim i = 1" writeToVBCode)
  (write-line "while i <= task.selection.count" writeToVBCode)
  (write-line "dim item = task.selection[i]" writeToVBCode)
  (write-line validityCheck writeToVBCode)
  (write-line decisionLine writeToVBCode)
  (write-line "item.update()" writeToVBCode)
  (write-line "end if" writeToVBCode)
  (write-line "i = i + 1" writeToVBCode)
  (write-line "end while" writeToVBCode)
  (close writeToVBCode)
  (Executescript vbCode sset)
  (vl-file-delete vbCode)
  (setq index nil
        operator nil
        parameterChoice nil
        valueChoice nil
        parameter nil
        dimIndexPara nil
        optionIndexPara nil
        valueChoice nil
        operator nil
        twoVariables nil
        stringValue1 nil
        stringValue2 nil
        dimIndexValue1 nil
        indexValue1 nil
        valueParameter1 nil
        value1Type nil
        optionIndexValue1 nil
        providedNumber1 nil
        stringValue2 nil
        dimIndexValue2 nil
        indexValue2 nil
        valueParameter2 nil
        value2Type nil
        optionIndexValue2 nil
        providedNumber2 nil
        dimIndexValue nil
        indexValue nil
        valueParameter nil
        valueType nil
        providedNumber nil
        dimIndexList nil
        optionIndexList nil
        dimCompare nil
        optionCompare nil
        dimElement nil
        dimComparison nil
        optionElement nil
        optionComparison nil
        adjustedValue nil
        validityCheck nil
        variableValue nil
        variableValue1 nil
        variableValue2 nil
        decisionLine nil)
  (princ)
  (END_ROUTINE)
);end defun
;**************************************************************************************************************************************************
(defun c:C1 ()
  (setq i 0
        sset (ssget '((0 . "MAPS_SOLID"))));end setq
  (OUTSIDE_LOOP_VARIABLES sset)
  (while(< i limit)
    (INSIDE_LOOP_VARIABLES sset i)
    (setq cNumber "1"
          connectionName c1Name)
    (if(= c1Spec "TDF")
      (if(wcmatch connectionName "TDF*")
        (setq newConnection "JF")
        (if(wcmatch connectionName "JF")
          (setq newConnection "JF-OFF")
          (if(wcmatch connectionName "JF-OFF")
            (setq newConnection "Cap")
            (if(wcmatch connectionName "Cap")
              (setq newConnection "RAW")
              (if(wcmatch connectionName "RAW")
                (setq newConnection "PG")
                (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                          (setq newConnection "1.5 flg out")
                          (if(wcmatch connectionName "1.5 flg out")
                            (setq newConnection "1.5 flg in")
                            (if(wcmatch connectionName "1.5 flg in")
                              (setq newConnection "JF 1\" + qt + \" DD")
                              (if(wcmatch connectionName "JF 1\" DD")
                                (setq newConnection "JF 1.5\" + qt + \" DD")
                                (if(wcmatch connectionName "JF 1.5\" DD")
                                  (setq newConnection "JF 2\" + qt + \" DD")
                                  (if(wcmatch connectionName "JF 2\" DD")
                                    (setq newConnection "JF 3\" + qt + \" DD")
                                    (if(wcmatch connectionName "JF 3\" DD")
                                      (setq newConnection "JF 4\" + qt + \" DD")
                                      (if(wcmatch connectionName "JF 4\" DD")
                                        (setq newConnection "TDF ")
      ) ) ) ) ) ) ) ) ) ) ) ) ) ) ) ) )
    (if(= c1Spec "Stand S&D")
      (if(wcmatch connectionName "Stand S&D")
        (setq newConnection "4S")
        (if(wcmatch connectionName "4S")
          (setq newConnection "Cap")
          (if(wcmatch connectionName "Cap")
            (setq newConnection "RAW")
            (if(wcmatch connectionName "RAW")
              (setq newConnection "PG")
              (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                        (setq newConnection "1.5 flg out")
                        (if(wcmatch connectionName "1.5 flg out")
                          (setq newConnection "1.5 flg in")
                          (if(wcmatch connectionName "1.5 flg in")
                            (setq newConnection "SD 1 SD")
                            (if(wcmatch connectionName "SD 1 SD")
                              (setq newConnection "SD 1.5 SD")
                              (if(wcmatch connectionName "SD 1.5 SD")
                                (setq newConnection "SD 2 SD")
                                (if(wcmatch connectionName "SD 2 SD")
                                  (setq newConnection "Stand S&D")
      ) ) ) ) ) ) ) ) ) ) ) ) ) )
    (if(= c1Spec "Flat S&D")
      (if(wcmatch connectionName "Flat S&D")
        (setq newConnection "4S")
        (if(wcmatch connectionName "4S")
          (setq newConnection "Cap")
          (if(wcmatch connectionName "Cap")
            (setq newConnection "RAW")
            (if(wcmatch connectionName "RAW")
              (setq newConnection "PG")
              (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                        (setq newConnection "1.5 flg out")
                        (if(wcmatch connectionName "1.5 flg out")
                          (setq newConnection "1.5 flg in")
                          (if(wcmatch connectionName "1.5 flg in")
                            (setq newConnection "SD 1 SD")
                            (if(wcmatch connectionName "SD 1 SD")
                              (setq newConnection "SD 1.5 SD")
                              (if(wcmatch connectionName "SD 1.5 SD")
                                (setq newConnection "SD 2 SD")
                                (if(wcmatch connectionName "SD 2 SD")
                                  (setq newConnection "Flat S&D")
      ) ) ) ) ) ) ) ) ) ) ) ) ) )
      ) ) )
      (if(or(wcmatch connectionName "TDF*")
            (wcmatch connectionName "JF")
            (wcmatch connectionName "JF-OFF")
            (wcmatch connectionName "JF 1\" DD")
            (wcmatch connectionName "JF 1.5\" DD")
            (wcmatch connectionName "JF 2\" DD")
            (wcmatch connectionName "JF 3\" DD")
            (wcmatch connectionName "JF 4\" DD"))
        (setq connectionGroup "Duct - Flg Connector")
        (if(or(wcmatch connectionName "Cap")
              (wcmatch connectionName "RAW")
              (wcmatch connectionName "PG"))
          (setq connectionGroup "Duct - Other")
          (if(or(wcmatch connectionName "1 Flg Out")
                (wcmatch connectionName "1 Flg In")
                (wcmatch connectionName "1.25 flg out")
                (wcmatch connectionName "1.25 flg in")
                (wcmatch connectionName "1.5 flg out")
                (wcmatch connectionName "1.5 flg in"))
            (setq connectionGroup "Duct - Flanged")
            (if(wcmatch connectionName "Tap Inside")
              (setq connectionGroup "Standard")
              (if(or(wcmatch connectionName "Flat S&D")
                   (wcmatch connectionName "4S")
                  (wcmatch connectionName "Stand S&D")
                  (wcmatch connectionName "SD 1 SD")
                  (wcmatch connectionName "SD 1.5 SD")
                  (wcmatch connectionName "SD 2 SD"))
              (setq connectionGroup "Duct - S&D")
      ) ) ) ) )
(write-line "dim qt = ASCII(34)" writeToVBCode)
(write-line (strcat "dim conNum = " cNumber) writeToVBCode)
(write-line (strcat "dim conName = \"" newConnection "\"") writeToVBCode)
(write-line (strcat "dim conGrp = \"" connectionGroup "\"") writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[conNum].value = conName" writeToVBCode)
(write-line "item.connector[conNum].locked = true" writeToVBCode)
(write-line "if item.connector[conNum].group <> conGrp then" writeToVBCode)
(write-line "connFind(conNum,conGrp,conName)" writeToVBCode)
(write-line "end if" writeToVBCode)
(if(and(= connectionGroup "Duct - Flg Connector")(= ItemCID "2"))
  (progn
    (write-line "if item.dim[6].value < 1.5 then" writeToVBCode)
    (write-line "item.dim[6].value = 1.5" writeToVBCode)
    (write-line "item.update()" writeToVBCode)
    (write-line "end if" writeToVBCode)
  );progn
);end if
(write-line "item.update()" writeToVBCode)
    (close writeToVBCode)
    (executescript vbCode sset)
    (setq writeToVBCode (open vbCode "w"))
    (princ (strcat "Connection " cNumber " changed from " connectionName " to " newConnection))(terpri)
    (setq i (1+ i))
  );end while
  (command "pselect" sset "")
  (command "regen")
  (princ)
(END_ROUTINE));end defun
;**************************************************************************************************************************************************
(defun c:C2 ()
  (setq i 0
        sset (ssget '((0 . "MAPS_SOLID"))));end setq
  (OUTSIDE_LOOP_VARIABLES sset)
  (while(< i limit)
    (INSIDE_LOOP_VARIABLES sset i)
    (setq cNumber "2"
          connectionName c2Name)
    (if(= c2Spec "TDF")
      (if(wcmatch connectionName "TDF*")
        (setq newConnection "JF")
        (if(wcmatch connectionName "JF")
          (setq newConnection "JF-OFF")
          (if(wcmatch connectionName "JF-OFF")
            (setq newConnection "Cap")
            (if(wcmatch connectionName "Cap")
              (setq newConnection "RAW")
              (if(wcmatch connectionName "RAW")
                (setq newConnection "PG")
                (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                          (setq newConnection "1.5 flg out")
                          (if(wcmatch connectionName "1.5 flg out")
                            (setq newConnection "1.5 flg in")
                            (if(wcmatch connectionName "1.5 flg in")
                              (setq newConnection "JF 1\" + qt + \" DD")
                              (if(wcmatch connectionName "JF 1\" DD")
                                (setq newConnection "JF 1.5\" + qt + \" DD")
                                (if(wcmatch connectionName "JF 1.5\" DD")
                                  (setq newConnection "JF 2\" + qt + \" DD")
                                  (if(wcmatch connectionName "JF 2\" DD")
                                    (setq newConnection "JF 3\" + qt + \" DD")
                                    (if(wcmatch connectionName "JF 3\" DD")
                                      (setq newConnection "JF 4\" + qt + \" DD")
                                      (if(wcmatch connectionName "JF 4\" DD")
                                        (setq newConnection "TDF ")
      ) ) ) ) ) ) ) ) ) ) ) ) ) ) ) ) )
    (if(= c2Spec "Stand S&D")
      (if(wcmatch connectionName "Stand S&D")
        (setq newConnection "4S")
        (if(wcmatch connectionName "4S")
          (setq newConnection "Cap")
          (if(wcmatch connectionName "Cap")
            (setq newConnection "RAW")
            (if(wcmatch connectionName "RAW")
              (setq newConnection "PG")
              (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                        (setq newConnection "1.5 flg out")
                        (if(wcmatch connectionName "1.5 flg out")
                          (setq newConnection "1.5 flg in")
                          (if(wcmatch connectionName "1.5 flg in")
                            (setq newConnection "SD 1 SD")
                            (if(wcmatch connectionName "SD 1 SD")
                              (setq newConnection "SD 1.5 SD")
                              (if(wcmatch connectionName "SD 1.5 SD")
                                (setq newConnection "SD 2 SD")
                                (if(wcmatch connectionName "SD 2 SD")
                                  (setq newConnection "Stand S&D")
      ) ) ) ) ) ) ) ) ) ) ) ) ) )
    (if(= c2Spec "Flat S&D")
      (if(wcmatch connectionName "Flat S&D")
        (setq newConnection "4S")
        (if(wcmatch connectionName "4S")
          (setq newConnection "Cap")
          (if(wcmatch connectionName "Cap")
            (setq newConnection "RAW")
            (if(wcmatch connectionName "RAW")
              (setq newConnection "PG")
              (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                        (setq newConnection "1.5 flg out")
                        (if(wcmatch connectionName "1.5 flg out")
                          (setq newConnection "1.5 flg in")
                          (if(wcmatch connectionName "1.5 flg in")
                            (setq newConnection "SD 1 SD")
                            (if(wcmatch connectionName "SD 1 SD")
                              (setq newConnection "SD 1.5 SD")
                              (if(wcmatch connectionName "SD 1.5 SD")
                                (setq newConnection "SD 2 SD")
                                (if(wcmatch connectionName "SD 2 SD")
                                  (setq newConnection "Flat S&D")
      ) ) ) ) ) ) ) ) ) ) ) ) ) )
      ) ) )
      (if(or(wcmatch connectionName "TDF*")
            (wcmatch connectionName "JF")
            (wcmatch connectionName "JF-OFF")
            (wcmatch connectionName "JF 1\" DD")
            (wcmatch connectionName "JF 1.5\" DD")
            (wcmatch connectionName "JF 2\" DD")
            (wcmatch connectionName "JF 3\" DD")
            (wcmatch connectionName "JF 4\" DD"))
        (setq connectionGroup "Duct - Flg Connector")
        (if(or(wcmatch connectionName "Cap")
              (wcmatch connectionName "RAW")
              (wcmatch connectionName "PG"))
          (setq connectionGroup "Duct - Other")
          (if(or(wcmatch connectionName "1 Flg Out")
                (wcmatch connectionName "1 Flg In")
                (wcmatch connectionName "1.25 flg out")
                (wcmatch connectionName "1.25 flg in")
                (wcmatch connectionName "1.5 flg out")
                (wcmatch connectionName "1.5 flg in"))
            (setq connectionGroup "Duct - Flanged")
            (if(wcmatch connectionName "Tap Inside")
            (setq connectionGroup "Duct - Flanged")
            (if(or(wcmatch connectionName "Flat S&D")
                  (wcmatch connectionName "4S")
                  (wcmatch connectionName "Stand S&D")
                  (wcmatch connectionName "SD 1 SD")
                  (wcmatch connectionName "SD 1.5 SD")
                  (wcmatch connectionName "SD 2 SD"))
              (setq connectionGroup "Duct - S&D")
      ) ) ) ) )
(write-line "dim qt = ASCII(34)" writeToVBCode)
(write-line (strcat "dim conNum = " cNumber) writeToVBCode)
(write-line (strcat "dim conName = \"" newConnection "\"") writeToVBCode)
(write-line (strcat "dim conGrp = \"" connectionGroup "\"") writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[conNum].value = conName" writeToVBCode)
(write-line "item.connector[conNum].locked = true" writeToVBCode)
(write-line "if item.connector[conNum].group <> conGrp then" writeToVBCode)
(write-line "connFind(conNum,conGrp,conName)" writeToVBCode)
(write-line "end if" writeToVBCode)
(if(and(= connectionGroup "Duct - Flg Connector")(= ItemCID "2"))
  (progn
    (write-line "if item.dim[7].value < 1.5 then" writeToVBCode)
    (write-line "item.dim[7].value = 1.5" writeToVBCode)
    (write-line "item.update()" writeToVBCode)
    (write-line "end if" writeToVBCode)
  );progn
);end if
(write-line "item.update()" writeToVBCode)
    (close writeToVBCode)
    (executescript vbCode sset)
    (setq writeToVBCode (open vbCode "w"))
    (princ (strcat "Connection " cNumber " changed from " connectionName " to " newConnection))(terpri)
    (setq i (1+ i))
  );end while
  (command "pselect" sset "")
  (command "regen")
  (princ)
(END_ROUTINE));end defun
;**************************************************************************************************************************************************
(defun c:Blockout_Dimensions ()
  ;(setq curUCSORG (getvar 'ucsorg))
  ;(setvar 'ucsorg "0.0 0.0 0.0")
  (if(not(or(= ucsName "WCS")(wcmatch ucsName "_@origin")))
    (progn
      (setq ucsOrg (getvar 'ucsorg)
            ucsXAxis (getvar 'ucsxdir)
            ucsYAxis (getvar 'ucsydir)
            ucsName (getvar 'ucsname)
            ucsAngle (getvar 'ucsaxisang)
      );end setq
      (command "_.UCS" "World" "")
      (command "_.UCS" (list 0 0 0);UCS origin point
                       (list (car ucsXAxis)(cadr ucsXAxis)(caddr ucsXAxis));UCS X axis point
                       (list (car ucsYAxis)(cadr ucsYAxis)(caddr ucsYAxis)) "" "");UCS Y axis point
      (if(not(or(= ucsName nil)(= ucsName "WCS")(= ucsName "")(wcmatch ucsName "_@origin")))
        (command "_.UCS" "Named" "Save" (strcat ucsName "_@origin") "")
      );end if
    );end progn
  );end if
  (setq i 0
        sset (ssget "_X" '((0 . "MAPS_SOLID")(-4 . "<OR")(300 . "Sleeve Rectangular")(300 . "Supply Blockout")(300 . "Return-Transfer Blockout")(300 . "Exhaust Blockout")(-4 . "OR>"))));end setq
  (OUTSIDE_LOOP_VARIABLES sset)
  (setvar "cmdecho" 0)
  (while(< i limit)
    (INSIDE_LOOP_VARIABLES sset i)
    (if(or(=(strcase ItemSourceFileName)(strcase "Sleeve Rectangular"))
          (=(strcase ItemSourceFileName)(strcase "Supply Blockout"))
          (=(strcase ItemSourceFileName)(strcase "Return-Transfer Blockout"))
          (=(strcase ItemSourceFileName)(strcase "Exhaust Blockout")))
      (progn
	;(setq xPts (list c4x c5x c6x c7x)
        ;      yPts (list c4y c5y c6y c7y)
        ;      leftestX (car xPts)
        ;      upestY (cadr yPts)
        ;);end setq
        ;(foreach elm xPts
        ;  (if(< elm leftestX)
        ;    (setq leftesetX elm)
        ;  );end if
        ;);foreach
        (setq pt1 (list c4x c4y c4z)
              pt2 (list c5x c5y c5z)
              pt3 (list c6x c6y c6z)
        );end setq
        (command "CAL" "translatedPt1=w2u(pt1)")
        (command "CAL" "translatedPt2=w2u(pt2)")
        (command "CAL" "translatedPt3=w2u(pt3)")
        (setvar 'osnapz 1)
        (initcommandversion 1)
        (setq oldCurrentLayer (getvar 'clayer))
        (command "LAYER" "SET" "M-AMC-GDIM-USER" "")
        (initcommandversion 2)
        (TRIG_MY_POINTS translatedPt1 nil nil translatedPt2 nil nil nil nil nil nil)
        (command "._dimlinear" translatedPt1 translatedPt2 side1Pos3)
        (TRIG_MY_POINTS translatedPt2 nil nil translatedPt3 nil nil nil nil nil nil)
        (command "._dimlinear" translatedPt2 translatedPt3 side1Pos3)
        (initcommandversion 1)
        (command "LAYER" "SET" oldCurrentLayer "")
        (setvar 'osnapz 0)
      );progn
    );end if
    (setq i (1+ i))
  );end while
  ;(setvar 'ucsorg curUCSORG)
  (if(not(or(= UCSname nil)(= UCSname "WCS")(= UCSname "")(= UCSname "Unnamed")))
    (command "_.UCS" "Named" "Restore" UCSname "")
    (if(not(= UCSname "_@origin"))
      (command "_.UCS" "Previous" "")
    );end if
  );end if
  (princ)
(END_ROUTINE)
);end defun
;**************************************************************************************************************************************************
(defun c:Fix_Elbows ()
  ;(setvar 'filedia 0)
  (setq i 0
        sset (ssget "_X" '((0 . "MAPS_SOLID")
                               (-4 . "<OR")
                                 (300 . "90Deg Welded Elbow")
                                 (300 . "45Deg Welded Elbow")
                               (-4 . "OR>"))));end setq
  (OUTSIDE_LOOP_VARIABLES sset)
  (while(< i limit)
    (close writeToVBCode)
    (setq writeToVBCode (open vbCode "w"))
    (INSIDE_LOOP_VARIABLES sset i)
    (setq oldItem ent
          oldItemDescription ItemDescription
          elbowAngle (rtos ItemLengthAngle 2 0)
          oldItemC1xyz (list c2x c2y c2z)
          oldItemC2xyz (list c3x c3y c3z))
    (if(wcmatch (strcase ItemDescription) "*HALF*")
      (progn
        (write-line (strcat "item.dim[\"Inner Radius\"].value = " (rtos dim2 2 0)) writeToVBCode)
        (write-line (strcat "item.dim[\"Angle\"].value = " elbowAngle) writeToVBCode)
        (write-line "item.update()" writeToVBCode)
      );end progn
      (progn
        (write-line (strcat "item.dim[\"Angle\"].value = " elbowAngle) writeToVBCode)
        (write-line "item.update()" writeToVBCode)
      );end progn
    );end if
    (close writeToVBCode)
    (command "attacher" oldItemC2xyz)
    (REDRAW)
    (command (takeoff "Q:/PM Shared/Libraries/Common/STANDARD ITEMS/2.) ROUND/#1 SPIRAL.itm" "" "") "")
    (command "._rotateatend" "180" "")
    (command "attachoff")
    (setq straightItem (entlast)
          ssStraightItem (ssadd straightItem))
    (INSIDE_LOOP_VARIABLES ssStraightItem 0)
    (setq straightC1xyz (list c1x c1y c1z)
          straightC2xyz (list c2x c2y c2z))
    (command "erase" oldItem "")
    (command "attacher" straightC1xyz)
    (REDRAW)
    (command (takeoff "Q:/PM Shared/Libraries/Common/STANDARD ITEMS/2.) ROUND/WELDED ELBOWS/Misc. Welded Elbow.ITM" "" "") "")
    (setq newItem (entlast)
          ssnewItem (ssadd newItem))
    (Executescript vbCode ssnewItem)
    (redraw)
    (command)(command)
    (INSIDE_LOOP_VARIABLES ssnewItem 0)
    (setq newItemC1xyz (list c2x c2y c2z)
          newItemC2xyz (list c3x c3y c3z))
    (command "erase" straightItem "")
    (command ".move" newItem "" newItemC1xyz straightC1xyz)
    (vl-file-delete vbCode)
    (setq i (1+ i))
  );end while
(END_ROUTINE));end defun
;**************************************************************************************************************************************************
(defun c:Automation1_Cdata ()
  (setq i 0
        sset (ssget '((0 . "MAPS_SOLID"))));end setq
  (OUTSIDE_LOOP_VARIABLES sset)
  (setq NewAutomation1 (getstring T "n/Enter the new Automation1 value (no commas): "))
  (if(and(not(= NewAutomation1 nil))(not(= NewAutomation1 "")))
    (while(< i limit)
      (INSIDE_LOOP_VARIABLES sset i)
      (vlax-put-property vla "CustomData" (strcat "Automation1" " = " NewAutomation1 ","))
      (setq i (1+ i))
    );end while
  );end if
(END_ROUTINE));end defun
;**************************************************************************************************************************************************
(defun c:Automation2_Cdata ()
  (setq i 0
        sset (ssget '((0 . "MAPS_SOLID"))));end setq
  (OUTSIDE_LOOP_VARIABLES sset)
  (setq NewAutomation2 (getstring T "n/Enter the new Automation2 value (no commas): "))
  (if(and(not(= NewAutomation2 nil))(not(= NewAutomation2 "")))
    (while(< i limit)
      (INSIDE_LOOP_VARIABLES sset i)
      (vlax-put-property vla "CustomData" (strcat "Automation2" " = " NewAutomation2 ","))
      (setq i (1+ i))
    );end while
  );end if
(END_ROUTINE));end defun
;**************************************************************************************************************************************************
(defun c:Tag_ID_Cdata ()
  (setq i 0
        sset (ssget '((0 . "MAPS_SOLID"))));end setq
  (OUTSIDE_LOOP_VARIABLES sset)
  (setq NewTag_ID (getstring T "n/Enter the new Tag_ID value (no commas): "))
  (if(and(not(= NewTag_ID nil))(not(= NewTag_ID "")))
    (while(< i limit)
      (INSIDE_LOOP_VARIABLES sset i)
      (vlax-put-property vla "CustomData" (strcat "Tag_ID" " = " NewTag_ID ","))
      (setq i (1+ i))
    );end while
  );end if
(END_ROUTINE));end defun
;**************************************************************************************************************************************************
(defun c:ItemCID_Cdata ()
  (setq i 0
        sset (ssget '((0 . "MAPS_SOLID"))));end setq
  (OUTSIDE_LOOP_VARIABLES sset)
  (setq NewItemCID (getstring T "n/Enter the new ItemCID value (no commas): "))
  (if(and(not(= NewItemCID nil))(not(= NewItemCID "")))
    (while(< i limit)
      (INSIDE_LOOP_VARIABLES sset i)
      (vlax-put-property vla "CustomData" (strcat "ItemCID" " = " NewItemCID ","))
      (setq i (1+ i))
    );end while
  );end if
(END_ROUTINE));end defun
;**************************************************************************************************************************************************
(defun c:Activity_#_Cdata ()
  (setq i 0
        sset (ssget '((0 . "MAPS_SOLID"))));end setq
  (OUTSIDE_LOOP_VARIABLES sset)
  (setq NewActivity_# (getstring T "n/Enter the new Activity_# value (no commas): "))
  (if(and(not(= NewActivity_# nil))(not(= NewActivity_# "")))
    (while(< i limit)
      (INSIDE_LOOP_VARIABLES sset i)
      (vlax-put-property vla "CustomData" (strcat "Activity_#" " = " NewActivity_# ","))
      (setq i (1+ i))
    );end while
  );end if
(END_ROUTINE));end defun
;**************************************************************************************************************************************************
(defun c:Manufacturer_Cdata ()
  (setq i 0
        sset (ssget '((0 . "MAPS_SOLID"))));end setq
  (OUTSIDE_LOOP_VARIABLES sset)
  (setq NewManufacturer (getstring T "n/Enter the new Manufacturer value (no commas): "))
  (if(and(not(= NewManufacturer nil))(not(= NewManufacturer "")))
    (while(< i limit)
      (INSIDE_LOOP_VARIABLES sset i)
      (vlax-put-property vla "CustomData" (strcat "Manufacturer" " = " NewManufacturer ","))
      (setq i (1+ i))
    );end while
  );end if
(END_ROUTINE));end defun
;**************************************************************************************************************************************************
(defun c:Model_Cdata ()
  (setq i 0
        sset (ssget '((0 . "MAPS_SOLID"))));end setq
  (OUTSIDE_LOOP_VARIABLES sset)
  (setq NewModel (getstring T "n/Enter the new Model value (no commas): "))
  (if(and(not(= NewModel nil))(not(= NewModel "")))
    (while(< i limit)
      (INSIDE_LOOP_VARIABLES sset i)
      (vlax-put-property vla "CustomData" (strcat "Model" " = " NewModel ","))
      (setq i (1+ i))
    );end while
  );end if
(END_ROUTINE));end defun
;**************************************************************************************************************************************************
(defun c:Size/Tonnage_Cdata ()
  (setq i 0
        sset (ssget '((0 . "MAPS_SOLID"))));end setq
  (OUTSIDE_LOOP_VARIABLES sset)
  (setq NewSize/Tonnage (getstring T "n/Enter the new Size/Tonnage value (no commas): "))
  (if(and(not(= NewSize/Tonnage nil))(not(= NewSize/Tonnage "")))
    (while(< i limit)
      (INSIDE_LOOP_VARIABLES sset i)
      (vlax-put-property vla "CustomData" (strcat "Size/Tonnage" " = " NewSize/Tonnage ","))
      (setq i (1+ i))
    );end while
  );end if
(END_ROUTINE));end defun
;**************************************************************************************************************************************************
(defun c:Tonnage_Cdata ()
  (setq i 0
        sset (ssget '((0 . "MAPS_SOLID"))));end setq
  (OUTSIDE_LOOP_VARIABLES sset)
  (setq Tonnage (getstring T "n/Enter the new Tonnage value (no commas): "))
  (if(and(not(= Tonnage nil))(not(= Tonnage "")))
    (while(< i limit)
      (INSIDE_LOOP_VARIABLES sset i)
      (vlax-put-property vla "CustomData" (strcat "Size/Tonnage" " = " Tonnage ","))
      (setq i (1+ i))
    );end while
  );end if
(END_ROUTINE));end defun
;**************************************************************************************************************************************************
(defun c:Size_Cdata ()
  (setq i 0
        sset (ssget '((0 . "MAPS_SOLID"))));end setq
  (OUTSIDE_LOOP_VARIABLES sset)
  (setq NewSize (getstring T "n/Enter the new Size value (no commas): "))
  (if(and(not(= NewSize nil))(not(= NewSize "")))
    (while(< i limit)
      (INSIDE_LOOP_VARIABLES sset i)
      (vlax-put-property vla "CustomData" (strcat "Size/Tonnage" " = " NewSize ","))
      (setq i (1+ i))
    );end while
  );end if
(END_ROUTINE));end defun
;**************************************************************************************************************************************************
(defun c:Weight_Cdata ()
  (setq i 0
        sset (ssget '((0 . "MAPS_SOLID"))));end setq
  (OUTSIDE_LOOP_VARIABLES sset)
  (setq NewWeight (getstring T "n/Enter the new Weight value (no commas): "))
  (if(and(not(= NewWeight nil))(not(= NewWeight "")))
    (while(< i limit)
      (INSIDE_LOOP_VARIABLES sset i)
      (vlax-put-property vla "CustomData" (strcat "Weight" " = " NewWeight ","))
      (setq i (1+ i))
    );end while
  );end if
(END_ROUTINE));end defun
;**************************************************************************************************************************************************
(defun c:CFM/ID#2_Cdata ()
  (setq i 0
        sset (ssget '((0 . "MAPS_SOLID"))));end setq
  (OUTSIDE_LOOP_VARIABLES sset)
  (setq NewCFM/ID#2 (getstring T "n/Enter the new CFM/ID#2 value (no commas): "))
  (if(and(not(= NewCFM/ID#2 nil))(not(= NewCFM/ID#2 "")))
    (while(< i limit)
      (INSIDE_LOOP_VARIABLES sset i)
      (vlax-put-property vla "CustomData" (strcat "CFM/ID#2" " = " NewCFM/ID#2 ","))
      (setq i (1+ i))
    );end while
  );end if
(END_ROUTINE));end defun
;**************************************************************************************************************************************************
(defun c:CFM_Cdata ()
  (setq i 0
        sset (ssget '((0 . "MAPS_SOLID"))));end setq
  (OUTSIDE_LOOP_VARIABLES sset)
  (setq NewCFM (getstring T "n/Enter the new CFM value (no commas): "))
  (if(and(not(= NewCFM nil))(not(= NewCFM "")))
    (while(< i limit)
      (INSIDE_LOOP_VARIABLES sset i)
      (vlax-put-property vla "CustomData" (strcat "CFM/ID#2" " = " NewCFM ","))
      (setq i (1+ i))
    );end while
  );end if
(END_ROUTINE));end defun
;**************************************************************************************************************************************************
(defun c:ID#2_Cdata ()
  (setq i 0
        sset (ssget '((0 . "MAPS_SOLID"))));end setq
  (OUTSIDE_LOOP_VARIABLES sset)
  (setq NewID#2 (getstring T "n/Enter the new ID#2 value (no commas): "))
  (if(and(not(= NewID#2 nil))(not(= NewID#2 "")))
    (while(< i limit)
      (INSIDE_LOOP_VARIABLES sset i)
      (vlax-put-property vla "CustomData" (strcat "CFM/ID#2" " = " NewID#2 ","))
      (setq i (1+ i))
    );end while
  );end if
(END_ROUTINE));end defun
;**************************************************************************************************************************************************
(defun c:Add_Tags ()
  (c:World_View)
  (Sleep_OSnap)
  (setq oldCurLay (getvar 'clayer)
        i 0
        sset (ssget "_X" '((0 . "MAPS_SOLID")
                            (-4 . "<OR")
                              (300 . "Diffusers")
                              (300 . "Rectangular Diffusers")
                              (300 . "Grille&Louver")
                              (300 . "Linear Diffusers")
                              (300 . "Fan Coil Unit")
                              (300 . "Inline Exhaust Fan")
                              (300 . "Upblast Exhaust Fan")
                              (300 . "Downblast Exhaust Fan")
                              (300 . "Ductless Fan Coil")
                              (300 . "Air Filtration System")
                            (-4 . "OR>")
                          )
             );end ssget
  );end setq
  (OUTSIDE_LOOP_VARIABLES sset)
  (while(< i limit)
    (INSIDE_LOOP_VARIABLES sset i)
    (setq tagIDtext Tag_ID
          tagIDINFOtext CFM/ID#2
          tagTOPNOTEStext ""
          tagBOTNOTEStext "")
    (initcommandversion 1)
    (setq anAirDevice (or
                      (wcmatch ItemSourceFileName "Diffusers")
                      (wcmatch ItemSourceFileName "Rectangular Diffusers")
                      (wcmatch ItemSourceFileName "Linear Diffusers")
                      (wcmatch ItemSourceFileName "Grille&Louver"))
          isEquipment (or
                      (wcmatch (strcase ItemSourceFileName) "FAN COIL UNIT")
                      (wcmatch (strcase ItemSourceFileName) "INLINE EXHAUST FAN")
                      (wcmatch (strcase ItemSourceFileName) "UPBLAST EXHAUST FAN")
                      (wcmatch (strcase ItemSourceFileName) "DUCTLESS FAN COIL")
                      (wcmatch (strcase ItemSourceFileName) "AIR FILTRATION SYSTEM"))
    );end setq
    (if(and(wcmatch (strcase ItemService) "*RETURN*")(not(wcmatch (strcase ItemService) "*WELD*")) anAirDevice)
      (progn
        (command "LAYER" "SET" "M-AMC-TAGS-RTRN" "")
        (setq tagLOOKUP1text "Return Air Tag"
              tagServicetext "R/A")
      );end progn
      (if(and(wcmatch (strcase ItemService) "*SUPPLY*")(not(wcmatch (strcase ItemService) "*WELD*")) anAirDevice)
        (progn
          (command "LAYER" "SET" "M-AMC-TAGS-SPLY" "")
          (setq tagLOOKUP1text "Supply Air Tag"
                tagServicetext "S/A")
        );end progn
        (if(and(wcmatch (strcase ItemService) "*EXHAUST*")(not(wcmatch (strcase ItemService) "*WELD*")) anAirDevice)
          (progn
            (command "LAYER" "SET" "M-AMC-TAGS-EXHA" "")
            (setq tagLOOKUP1text "Exhaust Air Tag"
                  tagServicetext "E/A")
          );end progn
          (if(and(wcmatch (strcase ItemService) "*OUTSIDE*")(not(wcmatch (strcase ItemService) "*WELD*")) anAirDevice)
            (progn
              (command "LAYER" "SET" "M-AMC-TAGS-OUTA" "")
              (setq tagLOOKUP1text "Outside Air Tag"
                    tagServicetext "O/A")
            );end progn
            (if(and(wcmatch (strcase ItemService) "*COMBUSTION*")(not(wcmatch (strcase ItemService) "*WELD*")) anAirDevice)
              (progn
                (command "LAYER" "SET" "M-AMC-TAGS-CBST" "")
                (setq tagLOOKUP1text "Combustion Air Tag"
                      tagServicetext "C/A")
              );end progn
              (if(and(wcmatch (strcase ItemService) "*TRANSFER*")(not(wcmatch (strcase ItemService) "*WELD*")) anAirDevice)
                (progn
                  (command "LAYER" "SET" "M-AMC-TAGS-XFER" "")
                  (setq tagLOOKUP1text "Transfer Air Tag"
                        tagServicetext "T/A")
                );end progn
                (if(and(wcmatch (strcase ItemService) "*EXHAUST*")(wcmatch (strcase ItemService) "*WELD*") anAirDevice)
                  (progn
                    (command "LAYER" "SET" "M-AMC-TAGS-EWLD" "")
                    (setq tagLOOKUP1text "Exhaust Air Tag"
                          tagServicetext "E/A")
                  );end progn
                  (if isEquipment
                    (progn
                      (command "LAYER" "SET" "M-AMC-TAGS-EQPM" "")
                      (setq tagLOOKUP1text "Equipment Tag"
                            tagServicetext "")
                    );end progn
    ) ) ) ) ) ) ) );end ifs
    (if anAirDevice
      (progn
        (if(and(wcmatch ItemDescription "*Rct Nck")(wcmatch (strcase ItemSourceFileName) "DIFFUSERS"))
          (setq tagSIZE1text (strcat (rtos(ROUND c1Width 1) 2 0) " x " (rtos(ROUND c1Depth 1) 2 0))
                tagSIZE2text (strcat (rtos(ROUND c2Width 1) 2 0) " x " (rtos(ROUND c2Depth 1) 2 0)))
          (if(and(wcmatch ItemDescription "*Rd Nck")(wcmatch (strcase ItemSourceFileName) "DIFFUSERS"))
            (setq tagSIZE1text (strcat (rtos(ROUND c5Width 1) 2 0) "~")
                  tagSIZE2text (strcat (rtos(ROUND c2Width 1) 2 0) " x " (rtos(ROUND c2Depth 1) 2 0)))
            (if(and(wcmatch ItemDescription "*Rct Nck")(wcmatch (strcase ItemSourceFileName) "RECTANGULAR DIFFUSERS"))
              (setq tagSIZE1text (strcat (rtos(ROUND dim2 1) 2 0) " x " (rtos(ROUND dim3 1) 2 0))
                    tagSIZE2text (strcat (rtos(ROUND dim7 1) 2 0) " x " (rtos(ROUND dim8 1) 2 0)))
              (if(and(wcmatch ItemDescription "*Rd Nck")(wcmatch (strcase ItemSourceFileName) "RECTANGULAR DIFFUSERS"))
                (setq tagSIZE1text (strcat (rtos(ROUND dim2 1) 2 0) "~")
                      tagSIZE2text (strcat (rtos(ROUND dim7 1) 2 0) " x " (rtos(ROUND dim8 1) 2 0)))
                (if(wcmatch ItemSourceFileName "Linear Diffusers")
                  (setq tagSIZE1text (strcat (rtos(ROUND c1Width 1) 2 0) "~")
                        tagSIZE2text (strcat (rtos(ROUND c2Width 1) 2 0) " x " (rtos(ROUND c2Depth 1) 2 0)))
                  (if(wcmatch ItemDescription "Round*")
                    (setq tagSIZE1text (strcat (rtos(ROUND c12Width 1) 2 0) "~")
                          tagSIZE2text "")
                    (if(wcmatch (strcase ItemSourceFileName) "GRILLE&LOUVER")
                      (setq tagSIZE1text (strcat (rtos(ROUND c1Width 1) 2 0) " x " (rtos(ROUND c1Depth 1) 2 0))
                            tagSIZE2text "")
                    );end if
                  );end if
                );end if
              );end if
            );end if
          );end if
        );end if
      );progn
      (if(or(wcmatch (strcase ItemSourceFileName) "FAN COIL UNIT")(wcmatch (strcase ItemSourceFileName) "INLINE EXHAUST FAN")(wcmatch (strcase ItemSourceFileName) "AIR FILTRATION SYSTEM"))
        (setq tagSIZE1text (strcat (rtos(ROUND c5Width 1) 2 0) " x " (rtos(ROUND c5Depth 1) 2 0))
              tagSIZE2text (strcat (rtos(ROUND c6Width 1) 2 0) " x " (rtos(ROUND c6Depth 1) 2 0)))
        (if(or(wcmatch (strcase ItemSourceFileName) "UPBLAST EXHAUST FAN")(wcmatch (strcase ItemSourceFileName) "DOWNBLAST EXHAUST FAN"))
          (setq tagSIZE1text (strcat (rtos(ROUND c1Width 1) 2 0) " x " (rtos(ROUND c1Depth 1) 2 0))
                tagSIZE2text "")
          (if(wcmatch (strcase ItemSourceFileName) "DUCTLESS FAN COIL")
            (setq tagSIZE1text ""
                  tagSIZE2text "")
    ) ) ) );end ifs
      (initcommandversion 2)
      (setvar 'attdia 0)
      (setvar 'attreq 0)
      (command "_.-insert" block_TagLink (list (+ (if(not(= c2x nil))c2x c1x) (+ 23 (if(not(= c2Depth nil))(/ c2Depth 2)1))) (- (if(not(= c2y nil))c2y c1y) (+ 8 (if(not(= c2Width nil))(/ c2Width 2)1))) (ROUNDUP (if(not(= c2z nil))c2z c1z) 12000)) "" "")
      (setvar 'attdia 1)
      (setvar 'attreq 1)
      (if(= tagIDtext nil)
        (setq tagIDtext "")
      );end if
      (if(= tagIDINFOtext nil)
        (setq tagIDINFOtext "")
      );end if
      (if(= tagTOPNOTEStext nil)
        (setq tagTOPNOTEStext "")
      );end if
      (if(= tagSIZE1text nil)
        (setq tagSIZE1text "")
      );end if
      (if(= tagSIZE2text nil)
        (setq tagSIZE2text "")
      );end if
      (if(= tagBOTNOTEStext nil)
        (setq tagBOTNOTEStext "")
      );end if
      (if(= tagLOOKUP1text nil)
        (setq tagLOOKUP1text "")
      );end if
      (CHANGE_ENTLAST_ATTRIBUTE "ID" tagIDtext)
      (CHANGE_ENTLAST_ATTRIBUTE "IDINFO" tagIDINFOtext)
      (CHANGE_ENTLAST_ATTRIBUTE "TOPNOTES" "")
      (CHANGE_ENTLAST_ATTRIBUTE "SIZE1" tagSIZE1text)
      (CHANGE_ENTLAST_ATTRIBUTE "SIZE2" tagSIZE2text)
      (CHANGE_ENTLAST_ATTRIBUTE "BOTNOTES" "")
      (CHANGE_ENTLAST_ATTRIBUTE "$/A" tagServicetext)
      ;(SET_ENTLAST_PROPERTY "Lookup1" tagLOOKUP1text)
    (setq i (1+ i))
  );end while
  (initcommandversion 1)
  (command "LAYER" "SET" oldCurrent "")
  (Wake_OSnap)
  (princ)
);end defun
;**************************************************************************************************************************************************
(defun c:Fix_Colors ()
  (setq oldCurrentLayer (getvar "CLAYER")
        supplyLowMasterColor 127
        supplyMediumMasterColor 137
        supplyHighMasterColor 147
        supplyUndergroundMasterColor 165
        returnLowMasterColor 217
        returnMediumMasterColor 227
        returnHighMasterColor 237
        exhaustLowMasterColor 17
        exhaustMediumMasterColor 27
        exhaustHighMasterColor 37
        exhaustInslabMasterColor 17
        exhaustPVCMasterColor 197
        combustionAirMasterColor 67
        transferAirMasterColor 77
        outsideAirMasterColor 87
        canvasMasterColor "WHITE"
        accessZoneMasterColor "CYAN"
        accessDoorMasterColor "BLUE"
        blockoutMasterColor "BLUE"
        steelMasterColor 46
        seismicMasterColor 55
        defaultMissedServiceType "WHITE"
        supplyTagColor 126
        returnTagColor 224
        exhaustTagColor 24
        weldedTagColor 44
        transferTagColor 77
        outsideTagColor 86
        combustionTagColor 66
        equipmentTagColor 152
        dimensionColor 160
        textColor 150
  );end setq
  (tblnext "layer" T)
  (initcommandversion 1)
  (while(setq evalLayer (cdr(assoc 2 (tblnext "layer"))))
    (setq -1MasterColorTest (or(wcmatch evalLayer "*-OINS-*")
                               (wcmatch evalLayer "*-IINS-*")
                               (wcmatch evalLayer "*-HIDE-*")
                               (wcmatch evalLayer "*-SYMB-*")
                               (wcmatch evalLayer "*-ALIA-*")
                               (wcmatch evalLayer "*-DIMN-*")
                               (wcmatch evalLayer "*-LEVE-*")
                               (wcmatch evalLayer "*-NUMB-*")
                               (wcmatch evalLayer "*-OSET-*")
                               (wcmatch evalLayer "*-SIZE-*")
                            );or
          MissedServiceTypeTest
                            (or
                               (wcmatch evalLayer "-OINS-*")
                               (wcmatch evalLayer "-IINS-*")
                               (wcmatch evalLayer "-HIDE-*")
                               (wcmatch evalLayer "-SYMB-*")
                               (wcmatch evalLayer "-ALIA-*")
                               (wcmatch evalLayer "-DIMN-*")
                               (wcmatch evalLayer "-LEVE-*")
                               (wcmatch evalLayer "-NUMB-*")
                               (wcmatch evalLayer "-OSET-*")
                               (wcmatch evalLayer "-SIZE-*")
                               (wcmatch evalLayer "-3DOB*")
                               (wcmatch evalLayer "-2DOB*")
                            );or
    );end setq
  (if MissedServiceTypeTest
    (command "LAYER" "COLOR" defaultMissedServiceType evalLayer "")
    (if(wcmatch evalLayer "M-HVAC-CNVS*")
      (command "LAYER" "COLOR" canvasMasterColor evalLayer "")
      (if(wcmatch evalLayer "M-HVAC-ACZN*")
        (command "LAYER" "COLOR" accessZoneMasterColor evalLayer "")
        (if(wcmatch evalLayer "M-HVAC-ACDR*")
          (command "LAYER" "COLOR" accessDoorMasterColor evalLayer "")
          (if(wcmatch evalLayer "M-HVAC-BKOT*")
            (command "LAYER" "COLOR" blockoutMasterColor evalLayer "")
            (if(wcmatch evalLayer "M-HVAC-STEL*")
              (command "LAYER" "COLOR" (rtos steelMasterColor 2 0) evalLayer "")
              (if(wcmatch evalLayer "M-HVAC-ANGL*")
                (command "LAYER" "COLOR" (rtos steelMasterColor 2 0) evalLayer "")
                (if(wcmatch evalLayer "M-HVAC-SEIS*")
                  (command "LAYER" "COLOR" (rtos seismicMasterColor 2 0) evalLayer "")
                ;(if(wcmatch evalLayer "M-AMC-TEXT*")
                  ;(command "LAYER" "COLOR" (rtos textColor 2 0) evalLayer "")
                ;(if(wcmatch evalLayer "M-AMC-GTXT-USER*")
                  ;(command "LAYER" "COLOR" (rtos textColor 2 0) evalLayer "")
                ;(if(wcmatch evalLayer "M-AMC-GDIM-USER*")
                  ;(command "LAYER" "COLOR" (rtos dimensionColor 2 0) evalLayer "")
  (if(wcmatch evalLayer "M-AMC-TAGS-SPLY")
    (command "LAYER" "COLOR" (rtos supplyTagColor 2 0) evalLayer "")
    (if(wcmatch evalLayer "M-AMC-TAGS-RTRN")
      (command "LAYER" "COLOR" (rtos returnTagColor 2 0) evalLayer "")
      (if(wcmatch evalLayer "M-AMC-TAGS-EXHA")
        (command "LAYER" "COLOR" (rtos exhaustTagColor 2 0) evalLayer "")
        (if(wcmatch evalLayer "M-AMC-TAGS-EWLD")
          (command "LAYER" "COLOR" (rtos weldedTagColor 2 0) evalLayer "")
          (if(wcmatch evalLayer "M-AMC-TAGS-XFER")
            (command "LAYER" "COLOR" (rtos transferTagColor 2 0) evalLayer "")
            (if(wcmatch evalLayer "M-AMC-TAGS-OUTA")
              (command "LAYER" "COLOR" (rtos outsideTagColor 2 0) evalLayer "")
              (if(wcmatch evalLayer "M-AMC-TAGS-CBST")
                (command "LAYER" "COLOR" (rtos combustionTagColor 2 0) evalLayer "")
                (if(wcmatch evalLayer "M-AMC-TAGS-EQPM")
                  (command "LAYER" "COLOR" (rtos equipmentTagColor 2 0) evalLayer "")
    (if(wcmatch evalLayer "M-HVAC-SLHG*")
      (command "LAYER" "COLOR" (rtos(- supplyLowMasterColor 4) 2 0) evalLayer "")
      (if(wcmatch evalLayer "M-HVAC-SLDL*")
        (command "LAYER" "COLOR" (rtos(- supplyLowMasterColor 7) 2 0) evalLayer "")
        (if(or(wcmatch evalLayer "M-HVAC-SLDE*")(and(wcmatch evalLayer "M-HVAC-SL*")-1MasterColorTest))
          (command "LAYER" "COLOR" (rtos(- supplyLowMasterColor 1) 2 0) evalLayer "")
          (if(and(wcmatch evalLayer "M-HVAC-SL*")(or(wcmatch evalLayer "*3DOB*")(wcmatch evalLayer "*2DOB*")))
            (command "LAYER" "COLOR" (rtos supplyLowMasterColor 2 0) evalLayer "")
            (if(wcmatch evalLayer "M-HVAC-SMHG*")
              (command "LAYER" "COLOR" (rtos(- supplyMediumMasterColor 4) 2 0) evalLayer "")
              (if(wcmatch evalLayer "M-HVAC-SMDL*")
                (command "LAYER" "COLOR" (rtos(- supplyMediumMasterColor 7) 2 0) evalLayer "")
                (if(or(wcmatch evalLayer "M-HVAC-SMDE*")(and(wcmatch evalLayer "M-HVAC-SM*")-1MasterColorTest))
                  (command "LAYER" "COLOR" (rtos(- supplyMediumMasterColor 1) 2 0) evalLayer "")
                  (if(and(wcmatch evalLayer "M-HVAC-SM*")(or(wcmatch evalLayer "*3DOB*")(wcmatch evalLayer "*2DOB*")))
                    (command "LAYER" "COLOR" (rtos supplyMediumMasterColor 2 0) evalLayer "")
                    (if(wcmatch evalLayer "M-HVAC-SHHG*")
                      (command "LAYER" "COLOR" (rtos(- supplyHighMasterColor 4) 2 0) evalLayer "")
                      (if(wcmatch evalLayer "M-HVAC-SHDL*")
                        (command "LAYER" "COLOR" (rtos(- supplyHighMasterColor 7) 2 0) evalLayer "")
                        (if(or(wcmatch evalLayer "M-HVAC-SHDE*")(and(wcmatch evalLayer "M-HVAC-SH*")-1MasterColorTest))
                          (command "LAYER" "COLOR" (rtos(- supplyHighMasterColor 1) 2 0) evalLayer "")
                          (if(and(wcmatch evalLayer "M-HVAC-SH*")(or(wcmatch evalLayer "*3DOB*")(wcmatch evalLayer "*2DOB*")))
                            (command "LAYER" "COLOR" (rtos supplyHighMasterColor 2 0) evalLayer "")
    (if(wcmatch evalLayer "M-HVAC-RLHG*")
      (command "LAYER" "COLOR" (rtos(- returnLowMasterColor 4) 2 0) evalLayer "")
      (if(wcmatch evalLayer "M-HVAC-RLDL*")
        (command "LAYER" "COLOR" (rtos(- returnLowMasterColor 7) 2 0) evalLayer "")
        (if(or(wcmatch evalLayer "M-HVAC-RLDE*")(and(wcmatch evalLayer "M-HVAC-RL*")-1MasterColorTest))
          (command "LAYER" "COLOR" (rtos(- returnLowMasterColor 1) 2 0) evalLayer "")
          (if(and(wcmatch evalLayer "M-HVAC-RL*")(or(wcmatch evalLayer "*3DOB*")(wcmatch evalLayer "*2DOB*")))
            (command "LAYER" "COLOR" (rtos returnLowMasterColor 2 0) evalLayer "")
            (if(wcmatch evalLayer "M-HVAC-RMHG*")
              (command "LAYER" "COLOR" (rtos(- returnMediumMasterColor 4) 2 0) evalLayer "")
              (if(wcmatch evalLayer "M-HVAC-RMDL*")
                (command "LAYER" "COLOR" (rtos(- returnMediumMasterColor 7) 2 0) evalLayer "")
                (if(or(wcmatch evalLayer "M-HVAC-RMDE*")(and(wcmatch evalLayer "M-HVAC-RM*")-1MasterColorTest))
                  (command "LAYER" "COLOR" (rtos(- returnMediumMasterColor 1) 2 0) evalLayer "")
                  (if(and(wcmatch evalLayer "M-HVAC-RM*")(or(wcmatch evalLayer "*3DOB*")(wcmatch evalLayer "*2DOB*")))
                    (command "LAYER" "COLOR" (rtos returnMediumMasterColor 2 0) evalLayer "")
                    (if(wcmatch evalLayer "M-HVAC-RHHG*")
                      (command "LAYER" "COLOR" (rtos(- returnHighMasterColor 4) 2 0) evalLayer "")
                      (if(wcmatch evalLayer "M-HVAC-RHDL*")
                        (command "LAYER" "COLOR" (rtos(- returnHighMasterColor 7) 2 0) evalLayer "")
                        (if(or(wcmatch evalLayer "M-HVAC-RHDE*")(and(wcmatch evalLayer "M-HVAC-RH*")-1MasterColorTest))
                          (command "LAYER" "COLOR" (rtos(- returnHighMasterColor 1) 2 0) evalLayer "")
                          (if(and(wcmatch evalLayer "M-HVAC-RH*")(or(wcmatch evalLayer "*3DOB*")(wcmatch evalLayer "*2DOB*")))
                            (command "LAYER" "COLOR" (rtos returnHighMasterColor 2 0) evalLayer "")
    (if(wcmatch evalLayer "M-HVAC-ELHG*")
      (command "LAYER" "COLOR" (rtos(- exhaustLowMasterColor 4) 2 0) evalLayer "")
      (if(wcmatch evalLayer "M-HVAC-ELDL*")
        (command "LAYER" "COLOR" (rtos(- exhaustLowMasterColor 7) 2 0) evalLayer "")
        (if(or(wcmatch evalLayer "M-HVAC-ELDE*")(and(wcmatch evalLayer "M-HVAC-EL*")-1MasterColorTest))
          (command "LAYER" "COLOR" (rtos(- exhaustLowMasterColor 1) 2 0) evalLayer "")
          (if(and(wcmatch evalLayer "M-HVAC-EL*")(or(wcmatch evalLayer "*3DOB*")(wcmatch evalLayer "*2DOB*")))
            (command "LAYER" "COLOR" (rtos exhaustLowMasterColor 2 0) evalLayer "")
            (if(wcmatch evalLayer "M-HVAC-EMHG*")
              (command "LAYER" "COLOR" (rtos(- exhaustMediumMasterColor 4) 2 0) evalLayer "")
              (if(wcmatch evalLayer "M-HVAC-EMDL*")
                (command "LAYER" "COLOR" (rtos(- exhaustMediumMasterColor 7) 2 0) evalLayer "")
                (if(or(wcmatch evalLayer "M-HVAC-EMDE*")(and(wcmatch evalLayer "M-HVAC-EM*")-1MasterColorTest))
                  (command "LAYER" "COLOR" (rtos(- exhaustMediumMasterColor 1) 2 0) evalLayer "")
                  (if(and(wcmatch evalLayer "M-HVAC-EM*")(or(wcmatch evalLayer "*3DOB*")(wcmatch evalLayer "*2DOB*")))
                    (command "LAYER" "COLOR" (rtos exhaustMediumMasterColor 2 0) evalLayer "")
                    (if(wcmatch evalLayer "M-HVAC-EHHG*")
                      (command "LAYER" "COLOR" (rtos(- exhaustHighMasterColor 4) 2 0) evalLayer "")
                      (if(wcmatch evalLayer "M-HVAC-EHDL*")
                        (command "LAYER" "COLOR" (rtos(- exhaustHighMasterColor 7) 2 0) evalLayer "")
                        (if(or(wcmatch evalLayer "M-HVAC-EHDE*")(and(wcmatch evalLayer "M-HVAC-EH*")-1MasterColorTest))
                          (command "LAYER" "COLOR" (rtos(- exhaustHighMasterColor 1) 2 0) evalLayer "")
                          (if(and(wcmatch evalLayer "M-HVAC-EH*")(or(wcmatch evalLayer "*3DOB*")(wcmatch evalLayer "*2DOB*")))
                            (command "LAYER" "COLOR" (rtos exhaustHighMasterColor 2 0) evalLayer "")
    (if(wcmatch evalLayer "M-HVAC-OAHG*")
      (command "LAYER" "COLOR" (rtos(- outsideAirMasterColor 4) 2 0) evalLayer "")
      (if(wcmatch evalLayer "M-HVAC-OADL*")
        (command "LAYER" "COLOR" (rtos(- outsideAirMasterColor 7) 2 0) evalLayer "")
        (if(or(wcmatch evalLayer "M-HVAC-OADE*")(and(wcmatch evalLayer "M-HVAC-OA*")-1MasterColorTest))
          (command "LAYER" "COLOR" (rtos(- outsideAirMasterColor 1) 2 0) evalLayer "")
          (if(and(wcmatch evalLayer "M-HVAC-OA*")(or(wcmatch evalLayer "*3DOB*")(wcmatch evalLayer "*2DOB*")))
            (command "LAYER" "COLOR" (rtos outsideAirMasterColor 2 0) evalLayer "")
    (if(wcmatch evalLayer "M-HVAC-CAHG*")
      (command "LAYER" "COLOR" (rtos(- combustionAirMasterColor 4) 2 0) evalLayer "")
      (if(wcmatch evalLayer "M-HVAC-CADL*")
        (command "LAYER" "COLOR" (rtos(- combustionAirMasterColor 7) 2 0) evalLayer "")
        (if(or(wcmatch evalLayer "M-HVAC-CADE*")(and(wcmatch evalLayer "M-HVAC-CA*")-1MasterColorTest))
          (command "LAYER" "COLOR" (rtos(- combustionAirMasterColor 1) 2 0) evalLayer "")
          (if(and(wcmatch evalLayer "M-HVAC-CA*")(or(wcmatch evalLayer "*3DOB*")(wcmatch evalLayer "*2DOB*")))
            (command "LAYER" "COLOR" (rtos combustionAirMasterColor 2 0) evalLayer "")
    (if(wcmatch evalLayer "M-HVAC-TAHG*")
      (command "LAYER" "COLOR" (rtos(- transferAirMasterColor 4) 2 0) evalLayer "")
      (if(wcmatch evalLayer "M-HVAC-TADL*")
        (command "LAYER" "COLOR" (rtos(- transferAirMasterColor 7) 2 0) evalLayer "")
        (if(or(wcmatch evalLayer "M-HVAC-TADE*")(and(wcmatch evalLayer "M-HVAC-TA*")-1MasterColorTest))
          (command "LAYER" "COLOR" (rtos(- transferAirMasterColor 1) 2 0) evalLayer "")
          (if(and(wcmatch evalLayer "M-HVAC-TA*")(or(wcmatch evalLayer "*3DOB*")(wcmatch evalLayer "*2DOB*")))
            (command "LAYER" "COLOR" (rtos transferAirMasterColor 2 0) evalLayer "")
    (if(wcmatch evalLayer "M-HVAC-SUHG*")
      (command "LAYER" "COLOR" (rtos(- supplyUndergroundMasterColor 4) 2 0) evalLayer "")
      (if(wcmatch evalLayer "M-HVAC-SUDL*")
        (command "LAYER" "COLOR" (rtos(- supplyUndergroundMasterColor 7) 2 0) evalLayer "")
        (if(or(wcmatch evalLayer "M-HVAC-SUDE*")(and(wcmatch evalLayer "M-HVAC-SU*")-1MasterColorTest))
          (command "LAYER" "COLOR" (rtos(- supplyUndergroundMasterColor 1) 2 0) evalLayer "")
          (if(and(wcmatch evalLayer "M-HVAC-SU*")(or(wcmatch evalLayer "*3DOB*")(wcmatch evalLayer "*2DOB*")))
            (command "LAYER" "COLOR" (rtos supplyUndergroundMasterColor 2 0) evalLayer "")
    (if(wcmatch evalLayer "M-HVAC-EIHG*")
      (command "LAYER" "COLOR" (rtos(- exhaustInslabMasterColor 4) 2 0) evalLayer "")
      (if(wcmatch evalLayer "M-HVAC-EIDL*")
        (command "LAYER" "COLOR" (rtos(- exhaustInslabMasterColor 7) 2 0) evalLayer "")
        (if(or(wcmatch evalLayer "M-HVAC-EIDE*")(and(wcmatch evalLayer "M-HVAC-EI*")-1MasterColorTest))
          (command "LAYER" "COLOR" (rtos(- exhaustInslabMasterColor 1) 2 0) evalLayer "")
          (if(and(wcmatch evalLayer "M-HVAC-EI*")(or(wcmatch evalLayer "*3DOB*")(wcmatch evalLayer "*2DOB*")))
            (command "LAYER" "COLOR" (rtos exhaustInslabMasterColor 2 0) evalLayer "")
    (if(wcmatch evalLayer "M-HVAC-EPHG*")
      (command "LAYER" "COLOR" (rtos(- exhaustPVCMasterColor 4) 2 0) evalLayer "")
      (if(wcmatch evalLayer "M-HVAC-EPDL*")
        (command "LAYER" "COLOR" (rtos(- exhaustPVCMasterColor 7) 2 0) evalLayer "")
        (if(or(wcmatch evalLayer "M-HVAC-EPDE*")(and(wcmatch evalLayer "M-HVAC-EP*")-1MasterColorTest))
          (command "LAYER" "COLOR" (rtos(- exhaustPVCMasterColor 1) 2 0) evalLayer "")
          (if(and(wcmatch evalLayer "M-HVAC-EP*")(or(wcmatch evalLayer "*3DOB*")(wcmatch evalLayer "*2DOB*")))
            (command "LAYER" "COLOR" (rtos exhaustPVCMasterColor 2 0) evalLayer "")
    ))))))))))))))))))))))))))))))))))))))))))))))))))))))))))))))))))))))))))));end ifs
  );end while
  (setvar "CLAYER" oldCurrentLayer)
  (setq evalLayer nil)
  (setq sset (ssget "_X" '((0 . "MAPS_SOLID"))));end setq
  (if(not(= sset nil))
    (progn
      (OUTSIDE_LOOP_VARIABLES nil)
      (write-line "requires task.selection" writeToVBCode)
      (write-line "dim i = 1" writeToVBCode)
      (write-line "dim qt = ASCII(34)" writeToVBCode)
      (write-line "while i <= task.selection.count" writeToVBCode)
      (write-line "dim item = task.selection[i]" writeToVBCode)
      (write-line "item.update()" writeToVBCode)
      (write-line "i = i + 1" writeToVBCode)
      (write-line "end while" writeToVBCode)
      (close writeToVBCode)
      (Executescript vbCode sset)
      (vl-file-delete vbCode)
    );progn
  );end if
  (princ)
  (END_ROUTINE)
);end defun
;**************************************************************************************************************************************************
(defun c:Set_Layer_Filters ()
  (vl-load-com)
  (setvar 'cmdecho 0)
    (progn
      (vl-catch-all-apply
        (function
          (lambda ()
            (vlax-for element(vla-Item(vla-GetExtensionDictionary(vla-get-Layers(vla-get-ActiveDocument(vlax-get-acad-object))))"ACAD_LAYERFILTERS")
              (vla-Delete element)
            (vlax-for element (vla-Item(vla-GetExtensionDictionary(vla-get-Layers(vla-get-ActiveDocument(vlax-get-acad-object))))"AcLyDictionary")
              (vla-Delete element)
            )
          );for
        );lamb
      );func
    );catch
  );progn
  (Command "-layer" "filter" "_N" "_P" "All" "NAME==\"~*|*\"" "" "01.) Non-XREF (Native)" "")
  
  (Command "-layer" "filter" "_N" "_P" "All" "NAME==\"*|*\"" "" "02.) XREF Only" "")
  (Command "-layer" "filter" "_N" "_P" "02.) XREF Only" "NAME==\"*|M-HVAC-*-NUMB-*\" or NAME==\"*|M-HVAC-*-SIZE-*\" or NAME==\"*|M-HVAC-*-ALIA-*\" or NAME==\"*|M-HVAC-*-LEVE-*\" or NAME==\"*|M-HVAC-*-DIMN-*\" or NAME==\"*|M-HVAC-*-OSET-*\" or NAME==\"*TEXT*\" or NAME==\"*GTXT*\"" "" "Xref Text" "")
  (Command "-layer" "filter" "_N" "_P" "Xref Text" "NAME==\"*|M-HVAC-*-NUMB-*\" or NAME==\"*|M-HVAC-*-SIZE-*\" or NAME==\"*|M-HVAC-*-ALIA-*\" or NAME==\"*|M-HVAC-*-LEVE-*\" or NAME==\"*|M-HVAC-*-DIMN-*\" or NAME==\"*|M-HVAC-*-OSET-*\"" "" "All CADmep Text" "")
  (Command "-layer" "filter" "_N" "_P" "Xref Text" "NAME==\"*|M-HVAC-*-SIZE-*\" or NAME==\"*|M-HVAC-*-ALIA-*\" or NAME==\"*|M-HVAC-*-LEVE-*\" or NAME==\"*|M-HVAC-*-DIMN-*\" or NAME==\"*|M-HVAC-*-OSET-*\"" "" "Numbers Excluded" "")
  (Command "-layer" "filter" "_N" "_P" "Xref Text" "NAME==\"*|M-HVAC-*-ALIA-*\"" "" "Aliases" "")
  (Command "-layer" "filter" "_N" "_P" "Xref Text" "NAME==\"*|M-HVAC-*-LEVE-*\"" "" "Elevations" "")
  (Command "-layer" "filter" "_N" "_P" "Xref Text" "NAME==\"*|M-HVAC-*-DIMN-*\"" "" "Lengths" "")
  (Command "-layer" "filter" "_N" "_P" "Xref Text" "NAME==\"*|M-HVAC-*-NUMB-*\"" "" "Numbers" "")
  (Command "-layer" "filter" "_N" "_P" "Xref Text" "NAME==\"*|M-HVAC-*-OSET-*\"" "" "Offsets" "")
  (Command "-layer" "filter" "_N" "_P" "Xref Text" "NAME==\"*|M-HVAC-*-SIZE-*\"" "" "Sizes" "")
  (Command "-layer" "filter" "_N" "_P" "Xref Text" "NAME==\"*GTXT*\" or NAME==\"*TEXT*\"" "" "Drawing Text" "")
  
  (Command "-layer" "filter" "_N" "_P" "All" "NAME==\"#-XREF-*\"" "" "03.) Xref Attachment" "")
  (Command "-layer" "filter" "_N" "_P" "All" "NAME==\"M-AMC-BKGD-*\"" "" "04.) Background" "")
  (Command "-layer" "filter" "_N" "_P" "All" "FROZEN==\"FALSE\"" "" "05.) Thawed" "")
  (Command "-layer" "filter" "_N" "_P" "05.) Thawed" "NAME==\"*|*\"" "" "Xref Thawed" "")
  (Command "-layer" "filter" "_N" "_P" "05.) Thawed" "NAME==\"~*|*\"" "" "DWG Thawed" "")
  (Command "-layer" "filter" "_N" "_P" "All" "FROZEN==\"TRUE\"" "" "06.) Frozen" "")
  (Command "-layer" "filter" "_N" "_P" "06.) Frozen" "NAME==\"*|*\"" "" "Xref Frozen" "")
  (Command "-layer" "filter" "_N" "_P" "06.) Frozen" "NAME==\"~*|*\"" "" "DWG Frozen" "")
  (Command "-layer" "filter" "_N" "_P" "All" "LOCKED==\"FALSE\"" "" "07.) Unlocked" "")
  (Command "-layer" "filter" "_N" "_P" "07.) Unlocked" "NAME==\"*|*\"" "" "Xref Unlocked" "")
  (Command "-layer" "filter" "_N" "_P" "07.) Unlocked" "NAME==\"~*|*\"" "" "DWG Unlocked" "")
  (Command "-layer" "filter" "_N" "_P" "All" "LOCKED==\"TRUE\"" "" "08.) Locked" "")
  (Command "-layer" "filter" "_N" "_P" "08.) Locked" "NAME==\"*|*\"" "" "Xref Locked" "")
  (Command "-layer" "filter" "_N" "_P" "08.) Locked" "NAME==\"~*|*\"" "" "DWG Locked" "")
  (Command "-layer" "filter" "_N" "_P" "All" "OFF==\"FALSE\"" "" "09.) On" "")
  (Command "-layer" "filter" "_N" "_P" "09.) On" "NAME==\"*|*\"" "" "Xref On" "")
  (Command "-layer" "filter" "_N" "_P" "09.) On" "NAME==\"~*|*\"" "" "DWG On" "")
  (Command "-layer" "filter" "_N" "_P" "All" "OFF==\"TRUE\"" "" "10.) Off" "")
  (Command "-layer" "filter" "_N" "_P" "10.) Off" "NAME==\"*|*\"" "" "Xref Off" "")
  (Command "-layer" "filter" "_N" "_P" "10.) Off" "NAME==\"~*|*\"" "" "DWG Off" "")
  (Command "-layer" "filter" "_N" "_P" "All" "PLOTTABLE==\"TRUE\"" "" "11.) Plottable" "")
  (Command "-layer" "filter" "_N" "_P" "11.) Plottable" "NAME==\"*|*\"" "" "Xref Off" "")
  (Command "-layer" "filter" "_N" "_P" "11.) Plottable" "NAME==\"~*|*\"" "" "DWG Off" "")
  (Command "-layer" "filter" "_N" "_P" "All" "PLOTTABLE==\"FALSE\"" "" "12.) Not Plottable" "")
  (Command "-layer" "filter" "_N" "_P" "12.) Not Plottable" "NAME==\"*|*\"" "" "Xref Off" "")
  (Command "-layer" "filter" "_N" "_P" "12.) Not Plottable" "NAME==\"~*|*\"" "" "DWG Off" "")

  (Command "-layer" "filter" "_N" "_P" "All" "NAME==\"*|*\"" "" "BACKGROUND" "")
  (Command "-layer" "filter" "_N" "_P" "BACKGROUND" "NAME==\"A-*\" or NAME==\"*ARCH*\"" "" "Arch" "")
  (Command "-layer" "filter" "_N" "_P" "BACKGROUND" "NAME==\"*Floorplan*\" or NAME==\"*Floor plan*\"" "" "Floorplan" "")
  (Command "-layer" "filter" "_N" "_P" "BACKGROUND" "NAME==\"*ReflectedCeilingPlan*\" or NAME==\"*Reflected Ceiling Plan*\" or NAME==\"*RCP*\"" "" "Floorplan" "")
  (Command "-layer" "filter" "_N" "_P" "BACKGROUND" "NAME==\"P-*\"" "" "Plumbing" "")
  (Command "-layer" "filter" "_N" "_P" "BACKGROUND" "NAME==\"S-*\"" "" "Struct" "")
  (Command "-layer" "filter" "_N" "_P" "BACKGROUND" "NAME==\"M-*\"" "" "HVAC" "")
  (Command "-layer" "filter" "_N" "_P" "BACKGROUND" "NAME==\"E-*\"" "" "Electrical" "")
  (Command "-layer" "filter" "_N" "_P" "BACKGROUND" "NAME==\"*GRID*\"" "" "Grid" "")
  (Command "-layer" "filter" "_N" "_P" "BACKGROUND" "NAME==\"*COLS*\"" "" "Cols" "")
  (Command "-layer" "filter" "_N" "_P" "BACKGROUND" "NAME==\"*DOOR*\"" "" "Doors" "")
  (Command "-layer" "filter" "_N" "_P" "BACKGROUND" "NAME==\"*GLAZ*\"" "" "Windows" "")
  (Command "-layer" "filter" "_N" "_P" "BACKGROUND" "NAME==\"*HRAL*\"" "" "Railing" "")
  (Command "-layer" "filter" "_N" "_P" "BACKGROUND" "NAME==\"*PAT*\"" "" "Patterns" "")
  (Command "-layer" "filter" "_N" "_P" "BACKGROUND" "NAME==\"*FURN*\"" "" "Furniture" "")
  (Command "-layer" "filter" "_N" "_P" "BACKGROUND" "NAME==\"*PAT*\"" "" "Patterns" "")
  (Command "-layer" "filter" "_N" "_P" "BACKGROUND" "NAME==\"*A-ANNO*\"" "" "Annotations" "")
  (Command "-layer" "filter" "_N" "_P" "BACKGROUND" "NAME==\"*DIM*\"" "" "Dimensions" "")

  (Command "-layer" "filter" "_N" "_P" "All" "NAME==\"*M-HVAC-*\"" "" "SERVICES" "")
  (Command "-layer" "filter" "_N" "_P" "SERVICES" "NAME==\"M-HVAC-CA*\"" "" "Combustion Air" "")
  (Command "-layer" "filter" "_N" "_P" "Combustion Air" "NAME==\"*|*\"" "" "Xref Combustion Air" "")
  (Command "-layer" "filter" "_N" "_P" "Combustion Air" "NAME==\"~*|*\"" "" "DWG Combustion Air" "")
  (Command "-layer" "filter" "_N" "_P" "SERVICES" "NAME==\"M-HVAC-EL*\"" "" "Exhaust Low Pressure" "")
  (Command "-layer" "filter" "_N" "_P" "Exhaust Low Pressure" "NAME==\"*|*\"" "" "Xref Exhaust Low Pressure" "")
  (Command "-layer" "filter" "_N" "_P" "Exhaust Low Pressure" "NAME==\"~*|*\"" "" "DWG Exhaust Low Pressure" "")
  (Command "-layer" "filter" "_N" "_P" "SERVICES" "NAME==\"M-HVAC-EM*\"" "" "Exhaust Medium Pressure" "")
  (Command "-layer" "filter" "_N" "_P" "Exhaust Medium Pressure" "NAME==\"*|*\"" "" "Xref Exhaust Medium Pressure" "")
  (Command "-layer" "filter" "_N" "_P" "Exhaust Medium Pressure" "NAME==\"~*|*\"" "" "DWG Exhaust Medium Pressure" "")
  (Command "-layer" "filter" "_N" "_P" "SERVICES" "NAME==\"M-HVAC-EH*\"" "" "Exhaust High Pressure" "")
  (Command "-layer" "filter" "_N" "_P" "Exhaust High Pressure" "NAME==\"*|*\"" "" "Xref Exhaust High Pressure" "")
  (Command "-layer" "filter" "_N" "_P" "Exhaust High Pressure" "NAME==\"~*|*\"" "" "DWG Exhaust High Pressure" "")
  (Command "-layer" "filter" "_N" "_P" "SERVICES" "NAME==\"M-HVAC-EW*\"" "" "Exhaust Welded" "")
  (Command "-layer" "filter" "_N" "_P" "Exhaust Welded" "NAME==\"*|*\"" "" "Xref Exhaust Welded" "")
  (Command "-layer" "filter" "_N" "_P" "Exhaust Welded" "NAME==\"~*|*\"" "" "DWG Exhaust Welded" "")
  (Command "-layer" "filter" "_N" "_P" "SERVICES" "NAME==\"M-HVAC-EP*\"" "" "Exhaust Air PVC" "")
  (Command "-layer" "filter" "_N" "_P" "Exhaust Air PVC" "NAME==\"*|*\"" "" "Xref Exhaust Air PVC" "")
  (Command "-layer" "filter" "_N" "_P" "Exhaust Air PVC" "NAME==\"~*|*\"" "" "DWG Exhaust Air PVC" "")
  (Command "-layer" "filter" "_N" "_P" "SERVICES" "NAME==\"M-HVAC-EI*\"" "" "Exhaust Air Inslab" "")
  (Command "-layer" "filter" "_N" "_P" "Exhaust Air Inslab" "NAME==\"*|*\"" "" "Xref Exhaust Air Inslab" "")
  (Command "-layer" "filter" "_N" "_P" "Exhaust Air Inslab" "NAME==\"~*|*\"" "" "DWG Exhaust Air Inslab" "")
  (Command "-layer" "filter" "_N" "_P" "SERVICES" "NAME==\"M-HVAC-OA*\"" "" "Outside Air" "")
  (Command "-layer" "filter" "_N" "_P" "Outside Air" "NAME==\"*|*\"" "" "Xref Outside Air" "")
  (Command "-layer" "filter" "_N" "_P" "Outside Air" "NAME==\"~*|*\"" "" "DWG Outside Air" "")
  (Command "-layer" "filter" "_N" "_P" "SERVICES" "NAME==\"M-HVAC-RL*\"" "" "Return Low Pressure" "")
  (Command "-layer" "filter" "_N" "_P" "Return Low Pressure" "NAME==\"*|*\"" "" "Xref Return Low Pressure" "")
  (Command "-layer" "filter" "_N" "_P" "Return Low Pressure" "NAME==\"~*|*\"" "" "DWG Return Low Pressure" "")
  (Command "-layer" "filter" "_N" "_P" "SERVICES" "NAME==\"M-HVAC-RM*\"" "" "Return Medium Pressure" "")
  (Command "-layer" "filter" "_N" "_P" "Return Medium Pressure" "NAME==\"*|*\"" "" "Xref Return Medium Pressure" "")
  (Command "-layer" "filter" "_N" "_P" "Return Medium Pressure" "NAME==\"~*|*\"" "" "DWG Return Medium Pressure" "")
  (Command "-layer" "filter" "_N" "_P" "SERVICES" "NAME==\"M-HVAC-RH*\"" "" "Return High Pressure" "")
  (Command "-layer" "filter" "_N" "_P" "Return High Pressure" "NAME==\"*|*\"" "" "Xref Return High Pressure" "")
  (Command "-layer" "filter" "_N" "_P" "Return High Pressure" "NAME==\"~*|*\"" "" "DWG Return High Pressure" "")
  (Command "-layer" "filter" "_N" "_P" "SERVICES" "NAME==\"M-HVAC-SL*\"" "" "Supply Low Pressure" "")
  (Command "-layer" "filter" "_N" "_P" "Supply Low Pressure" "NAME==\"*|*\"" "" "Xref Supply Low Pressure" "")
  (Command "-layer" "filter" "_N" "_P" "Supply Low Pressure" "NAME==\"~*|*\"" "" "DWG Supply Low Pressure" "")
  (Command "-layer" "filter" "_N" "_P" "SERVICES" "NAME==\"M-HVAC-SM*\"" "" "Supply Medium Pressure" "")
  (Command "-layer" "filter" "_N" "_P" "Supply Medium Pressure" "NAME==\"*|*\"" "" "Xref Supply Medium Pressure" "")
  (Command "-layer" "filter" "_N" "_P" "Supply Medium Pressure" "NAME==\"~*|*\"" "" "DWG Supply Medium Pressure" "")
  (Command "-layer" "filter" "_N" "_P" "SERVICES" "NAME==\"M-HVAC-SU*\"" "" "Supply High Pressure" "")
  (Command "-layer" "filter" "_N" "_P" "Supply High Pressure" "NAME==\"*|*\"" "" "Xref Supply High Pressure" "")
  (Command "-layer" "filter" "_N" "_P" "Supply High Pressure" "NAME==\"~*|*\"" "" "DWG Supply High Pressure" "")
  (Command "-layer" "filter" "_N" "_P" "SERVICES" "NAME==\"M-HVAC-SH*\"" "" "Supply Underground" "")
  (Command "-layer" "filter" "_N" "_P" "Supply Underground" "NAME==\"*|*\"" "" "Xref Supply Underground" "")
  (Command "-layer" "filter" "_N" "_P" "Supply Underground" "NAME==\"~*|*\"" "" "DWG Supply Underground" "")
  (Command "-layer" "filter" "_N" "_P" "SERVICES" "NAME==\"M-HVAC-TA*\"" "" "Transfer Air" "")
  (Command "-layer" "filter" "_N" "_P" "Transfer Air" "NAME==\"*|*\"" "" "Xref Transfer Air" "")
  (Command "-layer" "filter" "_N" "_P" "Transfer Air" "NAME==\"~*|*\"" "" "DWG Transfer Air" "")
  (Command "-layer" "filter" "_N" "_P" "SERVICES" "NAME==\"M-HVAC-TS*\"" "" "Trimble Seismic" "")
  (Command "-layer" "filter" "_N" "_P" "Trimble Seismic" "NAME==\"*|*\"" "" "Xref Trimble Seismic" "")
  (Command "-layer" "filter" "_N" "_P" "Trimble Seismic" "NAME==\"~*|*\"" "" "DWG Trimble Seismic" "")

  (Command "-layer" "filter" "_N" "_P" "All" "NAME==\"M-HVAC-*-A\" or NAME==\"M-HVAC-*-D\" or NAME==\"M-HVAC-*-I\" or NAME==\"M-HVAC-*-R\" or NAME==\"M-HVAC-*-EXST\"" "" "STATUS" "")
  (Command "-layer" "filter" "_N" "_P" "STATUS" "NAME==\"M-HVAC-*-A\"" "" "Approved" "")
  (Command "-layer" "filter" "_N" "_P" "STATUS" "NAME==\"M-HVAC-*-D\"" "" "Design" "")
  (Command "-layer" "filter" "_N" "_P" "STATUS" "NAME==\"M-HVAC-*-I\"" "" "Issued" "")
  (Command "-layer" "filter" "_N" "_P" "STATUS" "NAME==\"M-HVAC-*-R\"" "" "Revised" "")
  (Command "-layer" "filter" "_N" "_P" "STATUS" "NAME==\"M-HVAC-*-EXST\"" "" "Existing" "")

  (Command "-layer" "filter" "_N" "_P" "All" "NAME==\"M-HVAC-*-NUMB-*\" or NAME==\"M-HVAC-*-SIZE-*\" or NAME==\"M-HVAC-*-ALIA-*\" or NAME==\"M-HVAC-*-LEVE-*\" or NAME==\"M-HVAC-*-DIMN-*\" or NAME==\"M-HVAC-*-OSET-*\" or NAME==\"*TEXT*\" or NAME==\"*GTXT*\"" "" "TEXT" "")
  (Command "-layer" "filter" "_N" "_P" "TEXT" "NAME==\"M-HVAC-*-NUMB-*\" or NAME==\"M-HVAC-*-SIZE-*\" or NAME==\"M-HVAC-*-ALIA-*\" or NAME==\"M-HVAC-*-LEVE-*\" or NAME==\"M-HVAC-*-DIMN-*\" or NAME==\"M-HVAC-*-OSET-*\"" "" "All CADmep Text" "")
  (Command "-layer" "filter" "_N" "_P" "TEXT" "NAME==\"M-HVAC-*-SIZE-*\" or NAME==\"M-HVAC-*-ALIA-*\" or NAME==\"M-HVAC-*-LEVE-*\" or NAME==\"M-HVAC-*-DIMN-*\" or NAME==\"M-HVAC-*-OSET-*\"" "" "Numbers Excluded" "")
  (Command "-layer" "filter" "_N" "_P" "TEXT" "NAME==\"M-HVAC-*-ALIA-*\"" "" "Aliases" "")
  (Command "-layer" "filter" "_N" "_P" "TEXT" "NAME==\"M-HVAC-*-LEVE-*\"" "" "Elevations" "")
  (Command "-layer" "filter" "_N" "_P" "TEXT" "NAME==\"M-HVAC-*-DIMN-*\"" "" "Lengths" "")
  (Command "-layer" "filter" "_N" "_P" "TEXT" "NAME==\"M-HVAC-*-NUMB-*\"" "" "Numbers" "")
  (Command "-layer" "filter" "_N" "_P" "TEXT" "NAME==\"M-HVAC-*-OSET-*\"" "" "Offsets" "")
  (Command "-layer" "filter" "_N" "_P" "TEXT" "NAME==\"M-HVAC-*-SIZE-*\"" "" "Sizes" "")
  (Command "-layer" "filter" "_N" "_P" "TEXT" "NAME==\"*GTXT*\" or NAME==\"*TEXT*\"" "" "Drawing Text" "")

  (Command "-layer" "filter" "_N" "_P" "All" "NAME==\"*GDIM*\"" "" "Drawing Dimensions" "")
  (Command "-layer" "filter" "_N" "_P" "All" "NAME==\"M-HVAC-*-ISRT-*\"" "" "Trimble Points" "")
  (Command "-layer" "filter" "_N" "_P" "All" "NAME==\"M-HVAC-*-BKOT-*\"" "" "Blockouts" "")
  (Command "-layer" "filter" "_N" "_P" "All" "NAME==\"M-HVAC-*HG-*\"" "" "Hangers" "")
  (Command "-layer" "filter" "_N" "_P" "All" "NAME==\"M-AMC-TAGS-*\"" "" "Tags" "")
  (Command "-layer" "filter" "_N" "_P" "All" "NAME==\"M-HVAC-*FS-*\"" "" "Floor Support" "")
  (Command "-layer" "filter" "_N" "_P" "All" "NAME==\"M-HVAC-*-HIDE-*\"" "" "Hidden Lines" "")
  (Command "-layer" "filter" "_N" "_P" "All" "NAME==\"M-AMC-*-KYPL-*\"" "" "Keyplan Layers" "")
  (princ)
);end defun
;**************************************************************************************************************************************************
(defun c:ALL_ATT2TEXT ()
  (setq i 0
        sset (ssget "X" '((0 . "ATTDEF"))));end setq
  (if(not(= sset nil))
    (progn
      (OUTSIDE_LOOP_VARIABLES sset)
      (while(< i limit)
        (INSIDE_LOOP_VARIABLES sset i)
        (command "pselect" ent "")
        (command "TXT2MTXT")
        (setq i (1+ i))
      );end while
    );progn
  );end if
  (END_ROUTINE)
);end defun
;**************************************************************************************************************************************************
(defun c:Blockout_Text ()
  (command "erase" (ssget "X" '((2 . "BLOCKOUT_TEXT"))) "")
  (setq i 0
        orgDIMZIN (getvar "DIMZIN")
        sset (ssget "X" '((0 . "MAPS_SOLID")
                               (-4 . "<OR")
                                 (300 . "Supply Blockout")
                                 (300 . "Return-Transfer Blockout")
                                 (300 . "Exhaust Blockout")
                               (-4 . "OR>"))));end setq
  (OUTSIDE_LOOP_VARIABLES sset)
  (setvar "DIMZIN" 12)
  (while(< i limit)
    (INSIDE_LOOP_VARIABLES sset i)
    (GET_RELATIVE_ELEVATIONS)
    (setq BOSize (strcat "BO Size: " (rtos dim5 2 2) "x" (rtos dim6 2 2))
          BtmElev (strcat "BTM Elev: " (rtos(ROUND(- relativeBottomElevation dim8)0.5)3 2)))
    (if(= BOSize nil)(setq BOSize ""));end if
    (if(= BtmElev nil)(setq BtmElev ""));end if
    (initcommandversion 2)
    (setvar 'attdia 0)
    (setvar 'attreq 0)
    (command "_.-insert" block_BlockoutTextLink (list
                                                  (+(if(not(= translatedc2x nil))translatedc2x translatedc1x)1)
                                                  (+(if(not(= translatedc2y nil))translatedc2y translatedc1y)4)
                                                  (ROUNDUP(if(not(= translatedc2z nil))translatedc2z translatedc1z) 12000))
                                                "" "" "")
    (setvar 'attdia 1)
    (setvar 'attreq 1)
    (CHANGE_ENTLAST_ATTRIBUTE "BO_SIZE" BOSize)
    (CHANGE_ENTLAST_ATTRIBUTE "BTM_ELEV" BtmElev)
  (setq i (1+ i))
  );end while
  (setvar "DIMZIN" orgDIMZIN)
(END_ROUTINE));end defun
;**************************************************************************************************************************************************
(defun c:Get_SSET ()
  (setq i 0
        sset (ssget '((0 . "MAPS_SOLID"))));end setq
  (OUTSIDE_LOOP_VARIABLES sset)
  (INSIDE_LOOP_VARIABLES sset i)
(END_ROUTINE));end defun
;**************************************************************************************************************************************************
(defun c:Get_SSET_i ()
  (if(not(= sset nil))
    (progn
      (if(or(= i nil)(>= i limit))(progn(setq i (getint "Enter an \"integer\" as the desired selection set member index number:  "))(terpri)(setq iReset T)))
      (INSIDE_LOOP_VARIABLES sset i)
      (c:SELECT_ENTITY)
      (if(= iReset T)(setq i nil))
    );progn
    (progn
      (terpri)
      (princ "You must first establish your selection set.")
      (terpri)
      (princ)
      (c:Get_SSET)
    );progn
  );end if
(END_ROUTINE));end defun
;**************************************************************************************************************************************************
(defun c:Loop_SSET_Entities ()
  (OUTSIDE_LOOP_VARIABLES sset)
  (setq i 0);end setq
  (while(< i limit)
    (setq iReset nil)
    (c:Get_SSET_i)
    (REDRAW)
    (terpri)(princ i)(princ(strcat " of " (rtos limit 2 0)))
    (setq i (1+ i))
  );end while
(END_ROUTINE));end defun
;**************************************************************************************************************************************************
(defun c:Coordinate ()
  (setq Coordinate (getpoint)
        orgDIMZIN (getvar "DIMZIN"))
  (setvar "DIMZIN" 12)
  (terpri)
  (princ(strcat "x = " (rtos(car Coordinate)2 24)))
  (terpri)
  (princ(strcat "y = " (rtos(cadr Coordinate)2 24)))
  (terpri)
  (princ(strcat "z = " (rtos(caddr Coordinate)2 24)))
  (terpri)(princ)
  (setvar "DIMZIN" orgDIMZIN)
(END_ROUTINE));end defun
;**************************************************************************************************************************************************
(defun c:Select_Similar_SourceFileName&Description ()
  (setq i 0
        sset (ssget "_X" '((0 . "INSERT"))))
  (OUTSIDE_LOOP_VARIABLES nil)
  (INSIDE_LOOP_VARIABLES sset i)
  (if(wcmatch (cdr(nth 9 entlist)) "LEVEL 3_B-outs")
    (command "erase" SSentity "")
  );end if
  (princ)
);end defun
