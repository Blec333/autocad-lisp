;|
APPLOAD DEPENDENCIES TO INCLUDE

  UTILITIES:
    utilityFunctions.lsp

  COMMANDS:
    
|;

(defun c:Insulation_Specification_Cycle ()
  ;;;; ISC = CYCLES INSULATION SPECIFICATION OPTIONS WHERE APPROPRIATE
(OUTSIDE_LOOP_VARIABLES nil)
(write-line "requires task.selection" writeToVBCode)
(write-line "dim i = 1" writeToVBCode)
(write-line "task.beginprogress(task.selection.count)" writeToVBCode)
(write-line "while i <= task.selection.count" writeToVBCode)
(write-line "dim item = task.selection[i]" writeToVBCode)
(write-line "dim qt = ASCII(34)" writeToVBCode)
(write-line "REM ROUND EVALUATION" writeToVBCode)
(write-line "if item.insspec = \"INSULATION: Liner x 0.50\" then" writeToVBCode)
(write-line "item.insspec = \"INSULATION: Liner x 1.00\"" writeToVBCode)
(write-line "item.update()" writeToVBCode)
(write-line "elseif item.insspec = \"INSULATION: Liner x 1.00\" then" writeToVBCode)
(write-line "item.insspec = \"INSULATION: Liner x 1.50\"" writeToVBCode)
(write-line "item.update()" writeToVBCode)
(write-line "elseif item.insspec = \"INSULATION: Liner x 1.50\" then" writeToVBCode)
(write-line "item.insspec = \"INSULATION: Liner x 2.00\"" writeToVBCode)
(write-line "item.update()" writeToVBCode)
(write-line "elseif item.insspec = \"INSULATION: Liner x 2.00\" then" writeToVBCode)
(write-line "item.insspec = \"INSULATION: Duct Wrap x 1.00\"" writeToVBCode)
(write-line "item.update()" writeToVBCode)
(write-line "elseif item.insspec = \"INSULATION: Duct Wrap x 1.00\" then" writeToVBCode)
(write-line "item.insspec = \"INSULATION: Duct Wrap x 1.50\"" writeToVBCode)
(write-line "item.update()" writeToVBCode)
(write-line "elseif item.insspec = \"INSULATION: Duct Wrap x 1.50\" then" writeToVBCode)
(write-line "item.insspec = \"INSULATION: Duct Wrap x 2.00\"" writeToVBCode)
(write-line "item.update()" writeToVBCode)
(write-line "elseif item.insspec = \"INSULATION: Duct Wrap x 2.00\" then" writeToVBCode)
(write-line "item.insspec = \"INSULATION: Duct Wrap x 3.00\"" writeToVBCode)
(write-line "item.update()" writeToVBCode)
(write-line "elseif item.insspec = \"INSULATION: Duct Wrap x 3.00\" then" writeToVBCode)
(write-line "item.insspec = \"INSULATION: Duct Wrap x 4.00\"" writeToVBCode)
(write-line "item.update()" writeToVBCode)
(write-line "elseif item.insspec = \"INSULATION: Duct Wrap x 4.00\" then" writeToVBCode)
(write-line "item.insspec = \"INSULATION: Fire Wrap x 2.00\"" writeToVBCode)
(write-line "item.update()" writeToVBCode)
(write-line "elseif item.insspec = \"INSULATION: Fire Wrap x 2.00\" then" writeToVBCode)
(write-line "item.insspec = \"INSULATION: Fire Wrap x 3.00\"" writeToVBCode)
(write-line "item.update()" writeToVBCode)
(write-line "elseif item.insspec = \"INSULATION: Fire Wrap x 3.00\" then" writeToVBCode)
(write-line "item.insspec = \"INSULATION: Fire Wrap x 4.00\"" writeToVBCode)
(write-line "item.update()" writeToVBCode)
(write-line "elseif item.insspec = \"INSULATION: Fire Wrap x 4.00\" then" writeToVBCode)
(write-line "item.insspec = \"INSULATION: Fire Wrap x 5.00\"" writeToVBCode)
(write-line "item.update()" writeToVBCode)
(write-line "elseif item.insspec = \"INSULATION: Fire Wrap x 5.00\" then" writeToVBCode)
(write-line "item.insspec = \"INSULATION: Fire Wrap x 6.00\"" writeToVBCode)
(write-line "item.update()" writeToVBCode)
(write-line "elseif item.insspec = \"INSULATION: Fire Wrap x 6.00\" then" writeToVBCode)
(write-line "item.insspec = \"INSULATION: Fire Wrap x 7.00\"" writeToVBCode)
(write-line "item.update()" writeToVBCode)
(write-line "elseif item.insspec = \"INSULATION: Fire Wrap x 7.00\" then" writeToVBCode)
(write-line "item.insspec = \"INSULATION: Fire Wrap x 8.00\"" writeToVBCode)
(write-line "item.update()" writeToVBCode)
(write-line "elseif item.insspec = \"INSULATION: Fire Wrap x 8.00\" then" writeToVBCode)
(write-line "item.insspec = \"INSULATION: Fire Wrap x 9.00\"" writeToVBCode)
(write-line "item.update()" writeToVBCode)
(write-line "elseif item.insspec = \"INSULATION: Fire Wrap x 9.00\" then" writeToVBCode)
(write-line "item.insspec = \"INSULATION: Fire Wrap x 10.00\"" writeToVBCode)
(write-line "item.update()" writeToVBCode)
(write-line "elseif item.insspec = \"INSULATION: Fire Wrap x 10.00\" then" writeToVBCode)
(write-line "item.insspec = \"INSULATION: Double Wall x 0.50\"" writeToVBCode)
(write-line "item.update()" writeToVBCode)
(write-line "elseif item.insspec = \"INSULATION: Double Wall x 0.50\" then" writeToVBCode)
(write-line "item.insspec = \"INSULATION: Double Wall x 1.00\"" writeToVBCode)
(write-line "item.update()" writeToVBCode)
(write-line "elseif item.insspec = \"INSULATION: Double Wall x 1.00\" then" writeToVBCode)
(write-line "item.insspec = \"INSULATION: Double Wall x 1.50\"" writeToVBCode)
(write-line "item.update()" writeToVBCode)
(write-line "elseif item.insspec = \"INSULATION: Double Wall x 1.50\" then" writeToVBCode)
(write-line "item.insspec = \"INSULATION: Double Wall x 2.00\"" writeToVBCode)
(write-line "item.update()" writeToVBCode)
(write-line "elseif item.insspec = \"INSULATION: Double Wall x 2.00\" then" writeToVBCode)
(write-line "item.insspec = \"Off\"" writeToVBCode)
(write-line "item.update()" writeToVBCode)
(write-line "elseif item.insspec = \"Off\" then" writeToVBCode)
(write-line "item.insspec = \"None\"" writeToVBCode)
(write-line "item.update()" writeToVBCode)
(write-line "elseif item.insspec = \"Not Set\" then" writeToVBCode)
(write-line "item.insspec = \"INSULATION: Liner x 0.50\"" writeToVBCode)
(write-line "item.update()" writeToVBCode)
(write-line "end if" writeToVBCode)
(write-line "dim j = 1" writeToVBCode)
(write-line "while j < 100" writeToVBCode)
(write-line "task.message = \"You have just switched to:                            \" + item.insspec" writeToVBCode)
(write-line "j = j + 1" writeToVBCode)
(write-line "end while" writeToVBCode)
(write-line "i = i + 1" writeToVBCode)
(write-line "end while" writeToVBCode)
  (close writeToVBCode)
  (Executescript vbCode)
  (vl-file-delete vbCode)
  (prompt "Cycled to the next insulation specification option.")(princ)
  (princ)
(END_ROUTINE));end defun
