;|
APPLOAD DEPENDENCIES TO INCLUDE

  UTILITIES:
    utilityFunctions.lsp

  COMMANDS:
    
|;

(defun c:Adjust_Dampers ()
;;;; KS7L = Switch Damper to KS7L
  (OUTSIDE_LOOP_VARIABLES nil)
  (setq sset (ssget '((0 . "MAPS_SOLID"))))
  (initget 0 "C T 2 3 4 23 24 34 234 _ClearAll,C TapsOnly,T 2Trunk(D2),2 3Branch(D3),3 4Branch(D4),4 23(D2&D3),23 24(D2&D4),24 34(D3&D4),34 234(D2&D3&D4),234")
  (setq choice (getkword "\nEnter desired damper location(s): [Clear all/Tap Dampers/(2) Trunk D2/(3) Left Branch D3/(4) Right Branch D4/(23) D2 & D3/(24) D2 & D4/(34) D3 & D4/(234) D2 & D3 & D4] <Esc>")
        3/8thsRod "\"3/8\"+qt+\" ROD-L\""
        KS7L "\"KS7L-DN\""
        i 0);end setq
    (if(wcmatch choice "*TapsOnly*")
      (progn
        (write-line "requires task.selection" writeToVBCode)
        (write-line "dim i = 1" writeToVBCode)
        (write-line "dim qt = ASCII(34)" writeToVBCode)
        (write-line "while i <= task.selection.count" writeToVBCode)
        (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
        (write-line "i = i + 1" writeToVBCode)
        (write-line "end while" writeToVBCode)
        (close writeToVBCode)
        (Executescript vbCode sset)
        (vl-file-delete vbCode)
        (prompt "Added Tap dampers.")(princ)
        (princ)
      );progn
    (if(and(wcmatch choice "*Trunk*")(wcmatch choice "2*"))
      (progn
        (write-line "requires task.selection" writeToVBCode)
        (write-line "dim i = 1" writeToVBCode)
        (write-line "dim qt = ASCII(34)" writeToVBCode)
        (write-line "while i <= task.selection.count" writeToVBCode)
        (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
        (write-line "if item.dampers > 0 and item.dampers < 5 then" writeToVBCode)
        (write-line "if item.filename = \"Wye\" or item.filename = \"Lateral 45\" or item.filename = \"Conical Cross\" then" writeToVBCode)
        (write-line "if item.dim[\"D2 Trunk Diameter\"].value > 12 then" writeToVBCode)
        (write-line "item.damper[2].value = \"3/8\"+qt+\" ROD-D2\"" writeToVBCode)
        (write-line "item.damper[2].locked = true" writeToVBCode)
        (write-line "item.dim[\"D2 DAMPER COLLAR\"].value = 6" writeToVBCode)
        (write-line "elseif item.dim[\"D2 Trunk Diameter\"].value < 13 then" writeToVBCode)
        (write-line "item.damper[2].value = \"KS7L-D2\"" writeToVBCode)
        (write-line "item.damper[2].locked = true" writeToVBCode)
        (write-line "item.dim[\"D2 DAMPER COLLAR\"].value = 6" writeToVBCode)
        (write-line "item.update()" writeToVBCode)
        (write-line "end if" writeToVBCode)
        (write-line "end if" writeToVBCode)
        (write-line "end if" writeToVBCode)
        (write-line "i = i + 1" writeToVBCode)
        (write-line "end while" writeToVBCode)
        (close writeToVBCode)
        (Executescript vbCode sset)
        (vl-file-delete vbCode)
        (prompt "Added Trunk dampers to item(s).")(princ)
        (princ)
      );progn
      (if(and(wcmatch choice "*Branch*")(wcmatch choice "4*"))
        (progn
          (write-line "requires task.selection" writeToVBCode)
          (write-line "dim i = 1" writeToVBCode)
          (write-line "dim qt = ASCII(34)" writeToVBCode)
          (write-line "while i <= task.selection.count" writeToVBCode)
          (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
          (write-line "if item.dampers > 3 and item.dampers < 5 then" writeToVBCode)
          (write-line "if item.filename = \"Wye\" or item.filename = \"Lateral 45\" or item.filename = \"Conical Cross\" then" writeToVBCode)
          (write-line "if item.dim[\"D4 Right Branch Diameter\"].value > 12 then" writeToVBCode)
          (write-line "item.damper[4].value = \"3/8\"+qt+\" ROD-DN\"" writeToVBCode)
          (write-line "item.damper[4].locked = true" writeToVBCode)
          (write-line "item.update()" writeToVBCode)
          (write-line "elseif item.dim[\"D4 Right Branch Diameter\"].value < 13 then" writeToVBCode)
          (write-line "item.damper[4].value = \"KS7L-DN\"" writeToVBCode)
          (write-line "item.damper[4].locked = true" writeToVBCode)
          (write-line "item.update()" writeToVBCode)
          (write-line "end if" writeToVBCode)
          (write-line "if item.damper[2].value <> \"None\" then" writeToVBCode)
          (write-line "item.dim[\"D2 DAMPER COLLAR\"].value = 6" writeToVBCode)
          (write-line "item.update()" writeToVBCode)
          (write-line "end if" writeToVBCode)
          (write-line "end if" writeToVBCode)
          (write-line "end if" writeToVBCode)
          (write-line "i = i + 1" writeToVBCode)
          (write-line "end while" writeToVBCode)
          (close writeToVBCode)
          (Executescript vbCode sset)
          (vl-file-delete vbCode)
          (prompt "Added Right dampers to item(s).")(princ)
          (princ)
        );progn
        (if(and(wcmatch choice "*Branch*")(wcmatch choice "3*"))
          (progn
            (write-line "requires task.selection" writeToVBCode)
            (write-line "dim i = 1" writeToVBCode)
            (write-line "dim qt = ASCII(34)" writeToVBCode)
            (write-line "while i <= task.selection.count" writeToVBCode)
            (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
            (write-line "if item.dampers > 2 and item.dampers < 5 then" writeToVBCode)
            (write-line "if item.filename = \"Wye\" or item.filename = \"Lateral 45\" or item.filename = \"Conical Cross\" then" writeToVBCode)
            (write-line "if item.dim[\"D3 Left Branch Diameter\"].value > 12 then" writeToVBCode)
            (write-line "item.damper[3].value = \"3/8\"+qt+\" ROD-DN\"" writeToVBCode)
            (write-line "item.damper[3].locked = true" writeToVBCode)
            (write-line "item.update()" writeToVBCode)
            (write-line "elseif item.dim[\"D3 Left Branch Diameter\"].value < 13 then" writeToVBCode)
            (write-line "item.damper[3].value = \"KS7L-DN\"" writeToVBCode)
            (write-line "item.damper[3].locked = true" writeToVBCode)
            (write-line "item.update()" writeToVBCode)
            (write-line "end if" writeToVBCode)
            (write-line "if item.damper[2].value <> \"None\" then" writeToVBCode)
            (write-line "item.dim[\"D2 DAMPER COLLAR\"].value = 6" writeToVBCode)
            (write-line "item.update()" writeToVBCode)
            (write-line "end if" writeToVBCode)
            (write-line "end if" writeToVBCode)
            (write-line "end if" writeToVBCode)
            (write-line "i = i + 1" writeToVBCode)
            (write-line "end while" writeToVBCode)
            (close writeToVBCode)
            (Executescript vbCode sset)
            (vl-file-delete vbCode)
            (prompt "Added Left dampers to item(s).")(princ)
            (princ)
          );progn
          (if(wcmatch choice "Clear*")
            (progn
              (write-line "requires task.selection" writeToVBCode)
              (write-line "dim i = 1" writeToVBCode)
              (write-line "dim qt = ASCII(34)" writeToVBCode)
              (write-line "while i <= task.selection.count" writeToVBCode)
              (write-line "dim item = task.selection[i]" writeToVBCode)
        (write-line "if item.filename = \"Rd on Rd Conical 1'' Flg (for Damper)\" then" writeToVBCode)
        (write-line "item.damper[2].value = \"None\"" writeToVBCode)
        (write-line "item.damper[2].locked = true" writeToVBCode)
        (write-line "item.update()" writeToVBCode)
        (write-line "elseif item.filename = \"6'' Start Collar wFlg (for Damper)\" then" writeToVBCode)
        (write-line "item.damper[2].value = \"None\"" writeToVBCode)
        (write-line "item.damper[2].locked = true" writeToVBCode)
        (write-line "item.update()" writeToVBCode)
        (write-line "elseif item.filename = \"45Deg on Rd Saddle\" or item.filename = \"Rd on Rd Straight 1'' Flg\" then" writeToVBCode) 
        (write-line "item.damper[2].value = \"None\"" writeToVBCode)
        (write-line "item.damper[2].locked = true" writeToVBCode)
        (write-line "item.update()" writeToVBCode)
        (write-line "elseif item.filename = \"Flat Conical 1'' Flg (for Damper)\" or item.filename = \"45Deg Flat Saddle\" then" writeToVBCode)
        (write-line "item.damper[1].value = \"None\"" writeToVBCode)
        (write-line "item.damper[1].locked = true" writeToVBCode)
        (write-line "end if" writeToVBCode)
        (write-line "item.update()" writeToVBCode)
              (write-line "if item.dampers > 0 and item.dampers < 5 then" writeToVBCode)
              (write-line "if item.filename = \"Wye\" or item.filename = \"Lateral 45\" or item.filename = \"Conical Cross\" then" writeToVBCode)
              (write-line "item.damper[2].value = \"None\"" writeToVBCode)
              (write-line "item.damper[2].locked = true" writeToVBCode)
              (write-line "item.dim[\"D2 DAMPER COLLAR\"].value = 0" writeToVBCode)
              (write-line "item.update()" writeToVBCode)
              (write-line "item.damper[3].value = \"None\"" writeToVBCode)
              (write-line "item.damper[3].locked = true" writeToVBCode)
              (write-line "item.update()" writeToVBCode)
              (write-line "item.damper[4].value = \"None\"" writeToVBCode)
              (write-line "item.damper[4].locked = true" writeToVBCode)
              (write-line "item.update()" writeToVBCode)
              (write-line "end if" writeToVBCode)
              (write-line "end if" writeToVBCode)
              (write-line "i = i + 1" writeToVBCode)
              (write-line "end while" writeToVBCode)
              (close writeToVBCode)
              (Executescript vbCode sset)
              (vl-file-delete vbCode)
              (prompt "Cleared all (D2,D3,D4) dampers from item(s).")(princ)
              (princ)
            );progn
            (if(wcmatch choice "24(*")
              (progn
                (write-line "requires task.selection" writeToVBCode)
                (write-line "dim i = 1" writeToVBCode)
                (write-line "dim qt = ASCII(34)" writeToVBCode)
                (write-line "while i <= task.selection.count" writeToVBCode)
                (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                (write-line "if item.dampers > 3 and item.dampers < 5 then" writeToVBCode)
                (write-line "if item.filename = \"Wye\" or item.filename = \"Lateral 45\" or item.filename = \"Conical Cross\" then" writeToVBCode)
                (write-line "if item.dim[\"D2 Trunk Diameter\"].value > 12 then" writeToVBCode)
                (write-line "item.damper[2].value = \"3/8\"+qt+\" ROD-D2\"" writeToVBCode)
                (write-line "item.damper[2].locked = true" writeToVBCode)
                (write-line "item.dim[\"D2 DAMPER COLLAR\"].value = 6" writeToVBCode)
                (write-line "item.update()" writeToVBCode)
                (write-line "elseif item.dim[\"D2 Trunk Diameter\"].value < 13 then" writeToVBCode)
                (write-line "item.damper[2].value = \"KS7L-D2\"" writeToVBCode)
                (write-line "item.damper[2].locked = true" writeToVBCode)
                (write-line "item.dim[\"D2 DAMPER COLLAR\"].value = 6" writeToVBCode)
                (write-line "item.update()" writeToVBCode)
                (write-line "end if" writeToVBCode)
                (write-line "if item.dim[\"D4 Right Branch Diameter\"].value > 12 then" writeToVBCode)
                (write-line "item.damper[4].value = \"3/8\"+qt+\" ROD-DN\"" writeToVBCode)
                (write-line "item.damper[4].locked = true" writeToVBCode)
                (write-line "item.update()" writeToVBCode)
                (write-line "elseif item.dim[\"D4 Right Branch Diameter\"].value < 13 then" writeToVBCode)
                (write-line "item.damper[4].value = \"KS7L-DN\"" writeToVBCode)
                (write-line "item.damper[4].locked = true" writeToVBCode)
                (write-line "item.update()" writeToVBCode)
                (write-line "end if" writeToVBCode)
                (write-line "end if" writeToVBCode)
                (write-line "end if" writeToVBCode)
                (write-line "i = i + 1" writeToVBCode)
                (write-line "end while" writeToVBCode)
                (close writeToVBCode)
                (Executescript vbCode sset)
                (vl-file-delete vbCode)
                (prompt "Added Trunk and Right dampers to item(s).")(princ)
                (princ)
              );progn
              (if(wcmatch choice "23(*")
                (progn
                  (write-line "requires task.selection" writeToVBCode)
                  (write-line "dim i = 1" writeToVBCode)
                  (write-line "dim qt = ASCII(34)" writeToVBCode)
                  (write-line "while i <= task.selection.count" writeToVBCode)
                  (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                  (write-line "if item.dampers > 2 and item.dampers < 5 then" writeToVBCode)
                  (write-line "if item.filename = \"Wye\" or item.filename = \"Lateral 45\" or item.filename = \"Conical Cross\" then" writeToVBCode)
                  (write-line "if item.dim[\"D2 Trunk Diameter\"].value > 12 then" writeToVBCode)
                  (write-line "item.damper[2].value = \"3/8\"+qt+\" ROD-D2\"" writeToVBCode)
                  (write-line "item.damper[2].locked = true" writeToVBCode)
                  (write-line "item.dim[\"D2 DAMPER COLLAR\"].value = 6" writeToVBCode)
                  (write-line "item.update()" writeToVBCode)
                  (write-line "elseif item.dim[\"D2 Trunk Diameter\"].value < 13 then" writeToVBCode)
                  (write-line "item.damper[2].value = \"KS7L-D2\"" writeToVBCode)
                  (write-line "item.damper[2].locked = true" writeToVBCode)
                  (write-line "item.dim[\"D2 DAMPER COLLAR\"].value = 6" writeToVBCode)
                  (write-line "item.update()" writeToVBCode)
                  (write-line "end if" writeToVBCode)
                  (write-line "if item.dim[\"D3 Left Branch Diameter\"].value > 12 then" writeToVBCode)
                  (write-line "item.damper[3].value = \"3/8\"+qt+\" ROD-DN\"" writeToVBCode)
                  (write-line "item.damper[3].locked = true" writeToVBCode)
                  (write-line "item.update()" writeToVBCode)
                  (write-line "elseif item.dim[\"D3 Left Branch Diameter\"].value < 13 then" writeToVBCode)
                  (write-line "item.damper[3].value = \"KS7L-DN\"" writeToVBCode)
                  (write-line "item.damper[3].locked = true" writeToVBCode)
                  (write-line "item.update()" writeToVBCode)
                  (write-line "end if" writeToVBCode)
                  (write-line "end if" writeToVBCode)
                  (write-line "end if" writeToVBCode)
                  (write-line "i = i + 1" writeToVBCode)
                  (write-line "end while" writeToVBCode)
                  (close writeToVBCode)
                  (Executescript vbCode sset)
                  (vl-file-delete vbCode)
                  (prompt "Added Trunk and Left dampers to item(s).")(princ)
                  (princ)
                );progn
                (if(wcmatch choice "234(*")
                  (progn
                    (write-line "requires task.selection" writeToVBCode)
                    (write-line "dim i = 1" writeToVBCode)
                    (write-line "dim qt = ASCII(34)" writeToVBCode)
                    (write-line "while i <= task.selection.count" writeToVBCode)
                    (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                    (write-line "if item.dampers > 3 and item.dampers < 5 then" writeToVBCode)
                    (write-line "if item.filename = \"Wye\" or item.filename = \"Lateral 45\" or item.filename = \"Conical Cross\" then" writeToVBCode)
                    (write-line "if item.dim[\"D2 Trunk Diameter\"].value > 12 then" writeToVBCode)
                    (write-line "item.damper[2].value = \"3/8\"+qt+\" ROD-D2\"" writeToVBCode)
                    (write-line "item.damper[2].locked = true" writeToVBCode)
                    (write-line "item.dim[\"D2 DAMPER COLLAR\"].value = 6" writeToVBCode)
                    (write-line "item.update()" writeToVBCode)
                    (write-line "elseif item.dim[\"D2 Trunk Diameter\"].value < 13 then" writeToVBCode)
                    (write-line "item.damper[2].value = \"KS7L-D2\"" writeToVBCode)
                    (write-line "item.damper[2].locked = true" writeToVBCode)
                    (write-line "item.dim[\"D2 DAMPER COLLAR\"].value = 6" writeToVBCode)
                    (write-line "item.update()" writeToVBCode)
                    (write-line "end if" writeToVBCode)
                    (write-line "if item.dim[\"D3 Left Branch Diameter\"].value > 12 then" writeToVBCode)
                    (write-line "item.damper[3].value = \"3/8\"+qt+\" ROD-DN\"" writeToVBCode)
                    (write-line "item.damper[3].locked = true" writeToVBCode)
                    (write-line "item.update()" writeToVBCode)
                    (write-line "elseif item.dim[\"D3 Left Branch Diameter\"].value < 13 then" writeToVBCode)
                    (write-line "item.damper[3].value = \"KS7L-DN\"" writeToVBCode)
                    (write-line "item.damper[3].locked = true" writeToVBCode)
                    (write-line "item.update()" writeToVBCode)
                    (write-line "end if" writeToVBCode)
                    (write-line "if item.dim[\"D4 Right Branch Diameter\"].value > 12 then" writeToVBCode)
                    (write-line "item.damper[4].value = \"3/8\"+qt+\" ROD-DN\"" writeToVBCode)
                    (write-line "item.damper[4].locked = true" writeToVBCode)
                    (write-line "item.update()" writeToVBCode)
                    (write-line "elseif item.dim[\"D4 Right Branch Diameter\"].value < 13 then" writeToVBCode)
                    (write-line "item.damper[4].value = \"KS7L-DN\"" writeToVBCode)
                    (write-line "item.damper[4].locked = true" writeToVBCode)
                    (write-line "item.update()" writeToVBCode)
                    (write-line "end if" writeToVBCode)
                    (write-line "end if" writeToVBCode)
                    (write-line "end if" writeToVBCode)
                    (write-line "i = i + 1" writeToVBCode)
                    (write-line "end while" writeToVBCode)
                    (close writeToVBCode)
                    (Executescript vbCode sset)
                    (vl-file-delete vbCode)
                    (prompt "Added all (D2,D3,D4) dampers to item(s).")(princ)
                    (princ)
                  );progn
                  (if(wcmatch choice "34(*")
                    (progn
                      (write-line "requires task.selection" writeToVBCode)
                      (write-line "dim i = 1" writeToVBCode)
                      (write-line "dim qt = ASCII(34)" writeToVBCode)
                      (write-line "while i <= task.selection.count" writeToVBCode)
                      (write-line "dim item = task.selection[i]" writeToVBCode)
        (write-line "if item.filename = \"Rd on Rd Conical 1'' Flg (for Damper)\" then" writeToVBCode)
        (write-line "if item.dim[\"Branch Diameter\"].value > 12 then" writeToVBCode)
        (write-line "item.damper[2].value = \"3/8\"+qt+\" ROD-D2\"" writeToVBCode)
        (write-line "item.damper[2].locked = true" writeToVBCode)
        (write-line "elseif item.dim[\"Branch Diameter\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"6'' Start Collar wFlg (for Damper)\" then" writeToVBCode)
        (write-line "if item.dim[\"Diameter In\"].value > 12 then" writeToVBCode)
        (write-line "item.damper[2].value = \"3/8\"+qt+\" ROD-D2\"" writeToVBCode)
        (write-line "item.damper[2].locked = true" writeToVBCode)
        (write-line "elseif item.dim[\"Diameter In\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"45Deg on Rd Saddle\" or item.filename = \"Rd on Rd Straight 1'' Flg\" then" writeToVBCode)
        (write-line "if item.dim[\"Branch Diameter #1\"].value > 12 then" writeToVBCode)
        (write-line "item.damper[2].value = \"3/8\"+qt+\" ROD-D2\"" writeToVBCode)
        (write-line "item.damper[2].locked = true" writeToVBCode)
        (write-line "elseif item.dim[\"Branch Diameter #1\"].value < 13 then" writeToVBCode)
        (write-line "item.damper[2].value = \"KS7L-D2\"" writeToVBCode)
        (write-line "item.damper[2].locked = true" writeToVBCode)
        (write-line "end if" writeToVBCode)
        (write-line "item.update()" writeToVBCode)
        (write-line "elseif item.filename = \"Flat Conical 1'' Flg (for Damper)\" or item.filename = \"45Deg Flat Saddle\" then" writeToVBCode)
        (write-line "if item.dim[\"Branch Diameter\"].value > 12 then" writeToVBCode)
        (write-line "item.damper[1].value = \"3/8\"+qt+\" ROD-DN\"" writeToVBCode)
        (write-line "item.damper[1].locked = true" writeToVBCode)
        (write-line "elseif item.dim[\"Branch Diameter\"].value < 13 then" writeToVBCode)
        (write-line "item.damper[1].value = \"KS7L-DN\"" writeToVBCode)
        (write-line "item.damper[1].locked = true" writeToVBCode)
        (write-line "end if" writeToVBCode)
        (write-line "end if" writeToVBCode)
        (write-line "item.update()" writeToVBCode)
                      (write-line "if item.dampers > 3 and item.dampers < 5 then" writeToVBCode)
                      (write-line "if item.filename = \"Wye\" or item.filename = \"Lateral 45\" or item.filename = \"Conical Cross\" then" writeToVBCode)
                      (write-line "if item.dim[\"D3 Left Branch Diameter\"].value > 12 then" writeToVBCode)
                      (write-line "item.damper[3].value = \"3/8\"+qt+\" ROD-DN\"" writeToVBCode)
                      (write-line "item.damper[3].locked = true" writeToVBCode)
                      (write-line "item.update()" writeToVBCode)
                      (write-line "elseif item.dim[\"D3 Left Branch Diameter\"].value < 13 then" writeToVBCode)
                      (write-line "item.damper[3].value = \"KS7L-DN\"" writeToVBCode)
                      (write-line "item.damper[3].locked = true" writeToVBCode)
                      (write-line "item.update()" writeToVBCode)
                      (write-line "end if" writeToVBCode)
                      (write-line "if item.dim[\"D4 Right Branch Diameter\"].value > 12 then" writeToVBCode)
                      (write-line "item.damper[4].value = \"3/8\"+qt+\" ROD-DN\"" writeToVBCode)
                      (write-line "item.damper[4].locked = true" writeToVBCode)
                      (write-line "item.update()" writeToVBCode)
                      (write-line "elseif item.dim[\"D4 Right Branch Diameter\"].value < 13 then" writeToVBCode)
                      (write-line "item.damper[4].value = \"KS7L-DN\"" writeToVBCode)
                      (write-line "item.damper[4].locked = true" writeToVBCode)
                      (write-line "item.update()" writeToVBCode)
                      (write-line "end if" writeToVBCode)
                      (write-line "if item.damper[2].value <> \"None\" then" writeToVBCode)
                      (write-line "item.dim[\"D2 DAMPER COLLAR\"].value = 6" writeToVBCode)
                      (write-line "item.update()" writeToVBCode)
                      (write-line "end if" writeToVBCode)
                      (write-line "end if" writeToVBCode)
                      (write-line "end if" writeToVBCode)
                      (write-line "i = i + 1" writeToVBCode)
                      (write-line "end while" writeToVBCode)
                      (close writeToVBCode)
                      (Executescript vbCode sset)
                      (vl-file-delete vbCode)
                      (prompt "Added branch (D3,D4) dampers to item(s).")(princ)
                      (princ)
                    );progn
    ) ) ) ) ) ) ) ) )
(END_ROUTINE));end defun
