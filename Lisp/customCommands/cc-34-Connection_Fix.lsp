;|
APPLOAD DEPENDENCIES TO INCLUDE

  UTILITIES:
    utilityFunctions.lsp

  COMMANDS:
    
|;

(defun c:Connection_Fix ()
;CF = Fixes connections based on dimension standards
  (setq i 0
        sset (ssget '((0 . "MAPS_SOLID"))));end setq
  (OUTSIDE_LOOP_VARIABLES sset)
  (while(< i limit)
    (INSIDE_LOOP_VARIABLES sset i)
    (if(= c1Spec "TDF")
      (setq newConnection1 "TDF ")
      (if(= c1Spec "Stand S&D")
        (setq newConnection1 "Stand S&D")
      (if(= c1Spec "Flat S&D")
        (setq newConnection1 "Flat S&D")
    ) ) )
      (if(= c1Spec "TDF")
        (setq connectionGroup1 "Duct - Flg Connector")
        (if(or(= c1Spec "Stand S&D")(= c1Spec "Flat S&D"))
          (setq connectionGroup1 "Duct - S&D")
      ) )
    (if(= c2Spec "TDF")
      (setq newConnection2 "TDF ")
      (if(= c2Spec "Stand S&D")
        (setq newConnection2 "Stand S&D")
      (if(= c2Spec "Flat S&D")
        (setq newConnection2 "Flat S&D")
    ) ) )
      (if(= c2Spec "TDF")
        (setq connectionGroup2 "Duct - Flg Connector")
        (if(or(= c2Spec "Stand S&D")(= c1Spec "Flat S&D"))
          (setq connectionGroup2 "Duct - S&D")
      ) )
(write-line "dim c1Num = 1" writeToVBCode)
(write-line (strcat "dim c1Name = \"" newConnection1 "\"") writeToVBCode)
(write-line (strcat "dim c1Grp = \"" connectionGroup1 "\"") writeToVBCode)
(write-line "dim c2Num = 2" writeToVBCode)
(write-line (strcat "dim c2Name = \"" newConnection2 "\"") writeToVBCode)
(write-line (strcat "dim c2Grp = \"" connectionGroup2 "\"") writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(if(and(= connectionGroup1 "Duct - Flg Connector")(= ItemCID "2"))
  (progn
    (write-line "if item.dim[6].value < 1.5 then" writeToVBCode)
    (write-line "item.dim[6].value = 1.5" writeToVBCode)
    (write-line "item.update()" writeToVBCode)
    (write-line "end if" writeToVBCode)
  );progn
);end if
(if(and(= connectionGroup2 "Duct - Flg Connector")(= ItemCID "2"))
  (progn
    (write-line "if item.dim[7].value < 1.5 then" writeToVBCode)
    (write-line "item.dim[7].value = 1.5" writeToVBCode)
    (write-line "item.update()" writeToVBCode)
    (write-line "end if" writeToVBCode)
  );progn
);end if
(write-line "item.update()" writeToVBCode)
    (close writeToVBCode)
    (executescript vbCode sset)
    (princ (strcat "Connections are now " newConnection1 " & " newConnection2))(terpri)
    (setq i (1+ i))
  );end while
  (command "pselect" sset "")
  (command "regen")
  
  ;(command "pselect" sset "")
  ;(vla-highlight vla 1)
  ;(setq thisdrawing(vla-get-activedocument(vlax-get-acad-object)))
  ;(vla-Regen thisdrawing acAllViewports)
  (princ)
(END_ROUTINE))





;|CF = Fixes connections based on dimension standards
  (setq i 0
        sset (ssget '((0 . "MAPS_SOLID"))));end setq
  (OUTSIDE_LOOP_VARIABLES sset)
  (while(< i limit)
    (INSIDE_LOOP_VARIABLES sset i)
(if(not(wcmatch itemCutType "Equipment"))
  (progn
    (if(= c1Spec "TDF")
      (setq newConnection1 "TDF ")
      (if(= c1Spec "Stand S&D")
        (setq newConnection1 "Stand S&D")
      (if(= c1Spec "Flat S&D")
        (setq newConnection1 "Flat S&D")
    ) ) )
      (if(= c1Spec "TDF")
        (setq connectionGroup1 "Duct - Flg Connector")
        (if(or(= c1Spec "Stand S&D")(= c1Spec "Flat S&D"))
          (setq connectionGroup1 "Duct - S&D")
      ) )
    (if(= c2Spec "TDF")
      (setq newConnection2 "TDF ")
      (if(= c2Spec "Stand S&D")
        (setq newConnection2 "Stand S&D")
      (if(= c2Spec "Flat S&D")
        (setq newConnection2 "Flat S&D")
    ) ) )
      (if(= c2Spec "TDF")
        (setq connectionGroup2 "Duct - Flg Connector")
        (if(or(= c2Spec "Stand S&D")(= c1Spec "Flat S&D"))
          (setq connectionGroup2 "Duct - S&D")
      ) )
(write-line "if item.connectors > 1 and (wildcard(item.connector[2].group,\"Round*\") = 1) and item.cuttype <> \"Equipment\" and item.CID <> 8 then" writeToVBCode)
(write-line "if item.CID = 40 then" writeToVBCode)
(write-line "dim c1Num = 1" writeToVBCode)
(write-line "dim c1Name = \"Raw\"" writeToVBCode)
(write-line "dim c1Grp = \"Round Duct\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "if item.connector[c1Num].group <> c1Grp then" writeToVBCode)
(write-line "connFind(c1Num,c1Grp,c1Name)" writeToVBCode)
(write-line "end if" writeToVBCode)
(write-line "dim c2Num = 2" writeToVBCode)
(write-line "dim c2Name = \"Raw\"" writeToVBCode)
(write-line "dim c2Grp = \"Round Duct\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c2Num].value = c1Name" writeToVBCode)
(write-line "item.connector[c2Num].locked = true" writeToVBCode)
(write-line "if item.connector[c2Num].group <> c1Grp then" writeToVBCode)
(write-line "connFind(c2Num,c2Grp,c2Name)" writeToVBCode)
(write-line "end if" writeToVBCode)
(write-line "end if" writeToVBCode)
(write-line "elseif item.connectors > 1 and (wildcard(item.connector[2].group,\"Round*\") = 0) and item.cuttype <> \"Equipment\" and item.CID <> 8 then" writeToVBCode)
(write-line "dim c1Num = 1" writeToVBCode)
(write-line (strcat "dim c1Name = \"" newConnection1 "\"") writeToVBCode)
(write-line (strcat "dim c1Grp = \"" connectionGroup1 "\"") writeToVBCode)
(write-line "dim c2Num = 2" writeToVBCode)
(write-line (strcat "dim c2Name = \"" newConnection2 "\"") writeToVBCode)
(write-line (strcat "dim c2Grp = \"" connectionGroup2 "\"") writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(if(and(= connectionGroup1 "Duct - Flg Connector")(= ItemCID "2"))
  (progn
    (write-line "if item.dim[6].value < 1.5 then" writeToVBCode)
    (write-line "item.dim[6].value = 1.5" writeToVBCode)
    (write-line "item.update()" writeToVBCode)
    (write-line "end if" writeToVBCode)
  );progn
);end if
(if(and(= connectionGroup2 "Duct - Flg Connector")(= ItemCID "2"))
  (progn
    (write-line "if item.dim[7].value < 1.5 then" writeToVBCode)
    (write-line "item.dim[7].value = 1.5" writeToVBCode)
    (write-line "item.update()" writeToVBCode)
    (write-line "end if" writeToVBCode)
  );progn
);end if
(write-line "item.update()" writeToVBCode)
(write-line "end if" writeToVBCode)
    (close writeToVBCode)
    (executescript vbCode ent)
    (setq writeToVBCode nil
          writeToVBCode (open vbCode "w"))
    ;(princ (strcat "Connections are now " newConnection1 " & " newConnection2))(terpri)
    );progn
  );end if
    (setq i (1+ i))
  );end while
  (command "pselect" sset "")
  (command "regen")
  ;(command "pselect" sset "")
  ;(vla-highlight vla 1)
  ;(setq thisdrawing(vla-get-activedocument(vlax-get-acad-object)))
  ;(vla-Regen thisdrawing acAllViewports)
  (princ)
(END_ROUTINE));end defun
|;
