;|
APPLOAD DEPENDENCIES TO INCLUDE

  UTILITIES:
    utilityFunctions.lsp

  COMMANDS:
    
|;

(defun c:Update_Drawing ()
  (setvar "cmdecho" 0)
  (OUTSIDE_LOOP_VARIABLES nil)
  (terpri)(princ "Updating Blocks --")(princ)
  (if(not(= block_WorkingTemplateName nil))(command "._purge" "B" block_WorkingTemplateName "Y" (if(> (getvar 'cmdactive) 0) "Y")))
  (if(not(= block_WorkingTemplateName nil))(command "._insert" (strcat customBlocksDirectory "\\" block_WorkingTemplateName)(command)))
  (if(not(= block_ElevName nil))(command "._insert" (strcat customBlocksDirectory "\\" block_SizeName)(command))(command "attsync" "n" block_ElevName))
  (if(not(= block_SizeName nil))(command "._insert" (strcat customBlocksDirectory "\\" block_SizeName)(command))(command "attsync" "n" block_SizeName))
  (if(not(= block_DiamName nil))(command "._insert" (strcat customBlocksDirectory "\\" block_DiamName)(command))(command "attsync" "n" block_DiamName))
  (if(not(= block_TagName nil))(command "._insert" (strcat customBlocksDirectory "\\" block_TagName)(command))(command "attsync" "n" block_TagName))
  (if(not(= block_StampName nil))(command "._insert" (strcat customBlocksDirectory "\\" block_StampName)(command))(command "attsync" "n" block_StampName))
  (if(not(= block_TitleBlockName nil))(command "._insert" (strcat customBlocksDirectory "\\" block_TitleBlockName)(command))(command "attsync" "n" block_TitleBlockName))
  (Delete_TextDummy_Layer&Items)
  (c:Set_Layer_Filters)
  (terpri)(princ "-- Blocks Updated")(princ)
  (setq i 0
        sset (ssget "X" '((0 . "MAPS_SOLID"))));end setq
  (if(not(= sset nil))
    (progn
      (terpri)(princ "Updating Services and Specifications --")(princ)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if ((wildcard(item.service, \"*SUPPLY*\") = 1) and (wildcard(item.service, \"*2\"+qt+\"*\") = 1)) or ((wildcard(item.specification, \"*+2*\") = 1) and (wildcard(item.service, \"*None*\") = 1)) then" writeToVBCode)
(write-line "item.service = \"Supply Air (+2''WG) Low Pressure\"" writeToVBCode)
(write-line "item.update()" writeToVBCode)
(write-line "elseif ((wildcard(item.service, \"*SUPPLY*\") = 1) and (wildcard(item.service, \"*3\"+qt+\"*\") = 1)) or ((wildcard(item.specification, \"*+3*\") = 1) and (wildcard(item.service, \"*None*\") = 1)) then" writeToVBCode)
(write-line "item.service = \"Supply Air (+3''WG) Medium Pressure\"" writeToVBCode)
(write-line "item.update()" writeToVBCode)
(write-line "elseif ((wildcard(item.service, \"*SUPPLY*\") = 1) and (wildcard(item.service, \"*4\"+qt+\"*\") = 1)) or ((wildcard(item.specification, \"*+4*\") = 1) and (wildcard(item.service, \"*None*\") = 1)) then" writeToVBCode)
(write-line "item.service = \"Supply Air (+4''WG) High Pressure\"" writeToVBCode)
(write-line "item.update()" writeToVBCode)
(write-line "elseif ((wildcard(item.service, \"*SUPPLY*\") = 1) and (wildcard(item.service, \"*6\"+qt+\"*\") = 1)) or ((wildcard(item.specification, \"*+6*\") = 1) and (wildcard(item.service, \"*None*\") = 1)) then" writeToVBCode)
(write-line "item.service = \"Supply Air (+6''WG) High Pressure\"" writeToVBCode)
(write-line "item.update()" writeToVBCode)
(write-line "elseif ((wildcard(item.service, \"*SUPPLY*\") = 1) and (wildcard(item.service, \"*10\"+qt+\"*\") = 1)) or ((wildcard(item.specification, \"*+10*\") = 1) and (wildcard(item.service, \"*None*\") = 1)) then" writeToVBCode)
(write-line "item.service = \"Supply Air (+10''WG) High Pressure\"" writeToVBCode)
(write-line "item.update()" writeToVBCode)
(write-line "elseif ((wildcard(item.service, \"*RETURN*\") = 1) and (wildcard(item.service, \"*2\"+qt+\"*\") = 1)) then" writeToVBCode)
(write-line "item.service = \"Return Air (-2''WG) Low Pressure\"" writeToVBCode)
(write-line "item.update()" writeToVBCode)
(write-line "elseif ((wildcard(item.service, \"*RETURN*\") = 1) and (wildcard(item.service, \"*3\"+qt+\"*\") = 1)) then" writeToVBCode)
(write-line "item.service = \"Return Air (-3''WG) Medium Pressure\"" writeToVBCode)
(write-line "item.update()" writeToVBCode)
(write-line "elseif ((wildcard(item.service, \"*RETURN*\") = 1) and (wildcard(item.service, \"*4\"+qt+\"*\") = 1)) then" writeToVBCode)
(write-line "item.service = \"Return Air (-4''WG) High Pressure\"" writeToVBCode)
(write-line "item.update()" writeToVBCode)
(write-line "elseif ((wildcard(item.service, \"*RETURN*\") = 1) and (wildcard(item.service, \"*6\"+qt+\"*\") = 1)) then" writeToVBCode)
(write-line "item.service = \"Return Air (-6''WG) High Pressure\"" writeToVBCode)
(write-line "item.update()" writeToVBCode)
(write-line "elseif ((wildcard(item.service, \"*RETURN*\") = 1) and (wildcard(item.service, \"*10\"+qt+\"*\") = 1)) then" writeToVBCode)
(write-line "item.service = \"Return Air (-10''WG) High Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*2\"+qt+\"*\") = 1) or ((wildcard(item.specification, \"*-2*\") = 1) and (wildcard(item.specification, \"*WELD*\") = 0) and (wildcard(item.service, \"*None*\") = 1)) then" writeToVBCode)
(write-line "item.service = \"Exhaust Air (-2''WG) Low Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*3\"+qt+\"*\") = 1) or ((wildcard(item.specification, \"*-3*\") = 1) and (wildcard(item.specification, \"*WELD*\") = 0) and (wildcard(item.service, \"*None*\") = 1)) then" writeToVBCode)
(write-line "item.service = \"Exhaust Air (-3''WG) Medium Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*4\"+qt+\"*\") = 1) or ((wildcard(item.specification, \"*-4*\") = 1) and (wildcard(item.specification, \"*WELD*\") = 0) and (wildcard(item.service, \"*None*\") = 1)) then" writeToVBCode)
(write-line "item.service = \"Exhaust Air (-4''WG) High Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*6\"+qt+\"*\") = 1) or ((wildcard(item.specification, \"*-6*\") = 1) and (wildcard(item.specification, \"*WELD*\") = 0) and (wildcard(item.service, \"*None*\") = 1)) then" writeToVBCode)
(write-line "item.service = \"Exhaust Air (-6''WG) High Pressure\"" writeToVBCode)
(write-line "item.update()" writeToVBCode)
(write-line "elseif (wildcard(item.service, \"*EXHAUST*\") = 1) and (wildcard(item.service, \"*WELD*\") = 0) and (wildcard(item.service, \"*PVC*\") = 0) and (wildcard(item.service, \"*10\"+qt+\"*\") = 1) or ((wildcard(item.specification, \"*-10*\") = 1) and (wildcard(item.specification, \"*WELD*\") = 0) and (wildcard(item.service, \"*None*\") = 1)) then" writeToVBCode)
(write-line "item.service = \"Exhaust Air (-10''WG) High Pressure\"" writeToVBCode)
(write-line "item.update()" writeToVBCode)
(write-line "elseif ((wildcard(item.service, \"*EXHAUST*\") = 1) and (wildcard(item.service, \"*WELD*\") = 1) and (wildcard(item.service, \"*2\"+qt+\"*\") = 1)) or ((wildcard(item.specification, \"*WELD 2*\") = 1) and (wildcard(item.service, \"*None*\") = 1)) then" writeToVBCode)
(write-line "item.service = \"Exhaust Air Welded (-2''WG) Low Pressure\"" writeToVBCode)
(write-line "item.update()" writeToVBCode)
(write-line "elseif ((wildcard(item.service, \"*EXHAUST*\") = 1) and (wildcard(item.service, \"*WELD*\") = 1) and (wildcard(item.service, \"*3\"+qt+\"*\") = 1)) or ((wildcard(item.specification, \"*WELD 3*\") = 1) and (wildcard(item.service, \"*None*\") = 1)) then" writeToVBCode)
(write-line "item.service = \"Exhaust Air Welded (-3''WG) Medium Pressure\"" writeToVBCode)
(write-line "item.update()" writeToVBCode)
(write-line "elseif ((wildcard(item.service, \"*EXHAUST*\") = 1) and (wildcard(item.service, \"*WELD*\") = 1) and (wildcard(item.service, \"*4\"+qt+\"*\") = 1)) or ((wildcard(item.specification, \"*WELD 4*\") = 1) and (wildcard(item.service, \"*None*\") = 1)) then" writeToVBCode)
(write-line "item.service = \"Exhaust Air Welded (-4''WG) High Pressure\"" writeToVBCode)
(write-line "item.update()" writeToVBCode)
(write-line "elseif ((wildcard(item.service, \"*EXHAUST*\") = 1) and (wildcard(item.service, \"*WELD*\") = 1) and (wildcard(item.service, \"*6\"+qt+\"*\") = 1)) or ((wildcard(item.specification, \"*WELD 6*\") = 1) and (wildcard(item.service, \"*None*\") = 1)) then" writeToVBCode)
(write-line "item.service = \"Exhaust Air Welded (-6''WG) High Pressure\"" writeToVBCode)
(write-line "item.update()" writeToVBCode)
(write-line "elseif ((wildcard(item.service, \"*EXHAUST*\") = 1) and (wildcard(item.service, \"*WELD*\") = 1) and (wildcard(item.service, \"*10\"+qt+\"*\") = 1)) or ((wildcard(item.specification, \"*WELD 10*\") = 1) and (wildcard(item.service, \"*None*\") = 1)) then" writeToVBCode)
(write-line "item.service = \"Exhaust Air Welded (-10''WG) High Pressure\"" writeToVBCode)
(write-line "item.update()" writeToVBCode)
(write-line "elseif (wildcard(item.service, \"*EXHAUST*\") = 1) and (wildcard(item.service, \"*PVC*\") = 1) and (wildcard(item.service, \"*2\"+qt+\"*\") = 1) then" writeToVBCode)
(write-line "item.service = \"Exhaust Air PVC (-2''WG) Low Pressure\"" writeToVBCode)
(write-line "item.update()" writeToVBCode)
(write-line "elseif (wildcard(item.service, \"*COMBUSTION*\") = 1) and (wildcard(item.service, \"*2\"+qt+\"*\") = 1) then" writeToVBCode)
(write-line "item.service = \"Combustion Air (-2''WG) Low Pressure\"" writeToVBCode)
(write-line "item.update()" writeToVBCode)
(write-line "elseif (wildcard(item.service, \"*OUTSIDE*\") = 1) and (wildcard(item.service, \"*2\"+qt+\"*\") = 1) then" writeToVBCode)
(write-line "item.service = \"Outside Air (-2''WG) Low Pressure\"" writeToVBCode)
(write-line "item.update()" writeToVBCode)
(write-line "elseif (wildcard(item.service, \"*TRANSFER*\") = 1) and (wildcard(item.service, \"*2\"+qt+\"*\") = 1) then" writeToVBCode)
(write-line "item.service = \"Transfer Air (-2''WG) Low Pressure\"" writeToVBCode)
(write-line "item.update()" writeToVBCode)
(write-line "else" writeToVBCode)
(write-line "item.update()" writeToVBCode)
(write-line "end if" writeToVBCode)
(write-line "if (wildcard(item.service,\"*combustion*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*-10*\") = 1) and (wildcard(item.service,\"*weld*\") = 0) then" writeToVBCode)
(write-line "item.speclock = false" writeToVBCode)
(write-line "item.gaugelock = false" writeToVBCode)
(write-line "item.specification = \"-10''\"" writeToVBCode)
(write-line "item.speclock = true" writeToVBCode)
(write-line "item.update()" writeToVBCode)
(write-line "elseif (wildcard(item.service,\"*exhaust*\" + \"*-6*\") = 1) and (wildcard(item.service,\"*weld*\") = 0) then" writeToVBCode)
(write-line "item.speclock = false" writeToVBCode)
(write-line "item.gaugelock = false" writeToVBCode)
(write-line "item.specification = \"-6''\"" writeToVBCode)
(write-line "item.speclock = true" writeToVBCode)
(write-line "item.update()" writeToVBCode)
(write-line "elseif (wildcard(item.service,\"*exhaust*\" + \"*-4*\") = 1) and (wildcard(item.service,\"*weld*\") = 0) then" writeToVBCode)
(write-line "item.speclock = false" writeToVBCode)
(write-line "item.gaugelock = false" writeToVBCode)
(write-line "item.specification = \"-4''\"" writeToVBCode)
(write-line "item.speclock = true" writeToVBCode)
(write-line "item.update()" writeToVBCode)
(write-line "elseif (wildcard(item.service,\"*exhaust*\" + \"*inslab*\") = 1) and (wildcard(item.service,\"*weld*\") = 0) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*low*\") = 1) and (wildcard(item.service,\"*weld*\") = 0) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*exhaust*\" + \"*medium*\") = 1) and (wildcard(item.service,\"*weld*\") = 0) then" writeToVBCode)
(write-line "item.speclock = false" writeToVBCode)
(write-line "item.gaugelock = false" writeToVBCode)
(write-line "item.specification = \"-3''\"" writeToVBCode)
(write-line "item.speclock = true" writeToVBCode)
(write-line "item.update()" writeToVBCode)
(write-line "elseif (wildcard(item.service,\"*exhaust*\" + \"*weld*\" + \"*-10*\") = 1) then" writeToVBCode)
(write-line "item.speclock = false" writeToVBCode)
(write-line "item.gaugelock = false" writeToVBCode)
(write-line "item.specification = \"WELD 10\" + qt + \" 5FT\"" writeToVBCode)
(write-line "item.speclock = true" writeToVBCode)
(write-line "item.update()" writeToVBCode)
(write-line "elseif (wildcard(item.service,\"*exhaust*\" + \"*weld*\" + \"*-6*\") = 1) then" writeToVBCode)
(write-line "item.speclock = false" writeToVBCode)
(write-line "item.gaugelock = false" writeToVBCode)
(write-line "item.specification = \"WELD 6\" + qt + \" 5FT\"" writeToVBCode)
(write-line "item.speclock = true" writeToVBCode)
(write-line "item.update()" writeToVBCode)
(write-line "elseif (wildcard(item.service,\"*exhaust*\" + \"*weld*\" + \"*-4*\") = 1) then" writeToVBCode)
(write-line "item.speclock = false" writeToVBCode)
(write-line "item.gaugelock = false" writeToVBCode)
(write-line "item.specification = \"WELD 4\" + qt + \" 5FT\"" writeToVBCode)
(write-line "item.speclock = true" writeToVBCode)
(write-line "item.update()" writeToVBCode)
(write-line "elseif (wildcard(item.service,\"*exhaust*\" + \"*weld*\" + \"*-2*\") = 1) then" writeToVBCode)
(write-line "item.speclock = false" writeToVBCode)
(write-line "item.gaugelock = false" writeToVBCode)
(write-line "item.specification = \"WELD 2\" + qt + \" 5FT\"" writeToVBCode)
(write-line "item.speclock = true" writeToVBCode)
(write-line "item.update()" writeToVBCode)
(write-line "elseif (wildcard(item.service,\"*outside*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*return*\" + \"*-10*\") = 1) then" writeToVBCode)
(write-line "item.speclock = false" writeToVBCode)
(write-line "item.gaugelock = false" writeToVBCode)
(write-line "item.specification = \"-10''\"" writeToVBCode)
(write-line "item.speclock = true" writeToVBCode)
(write-line "item.update()" writeToVBCode)
(write-line "elseif (wildcard(item.service,\"*return*\" + \"*-6*\") = 1) then" writeToVBCode)
(write-line "item.speclock = false" writeToVBCode)
(write-line "item.gaugelock = false" writeToVBCode)
(write-line "item.specification = \"-6''\"" writeToVBCode)
(write-line "item.speclock = true" writeToVBCode)
(write-line "item.update()" writeToVBCode)
(write-line "elseif (wildcard(item.service,\"*return*\" + \"*-4*\") = 1) then" writeToVBCode)
(write-line "item.speclock = false" writeToVBCode)
(write-line "item.gaugelock = false" writeToVBCode)
(write-line "item.specification = \"-4''\"" writeToVBCode)
(write-line "item.speclock = true" writeToVBCode)
(write-line "item.update()" writeToVBCode)
(write-line "elseif (wildcard(item.service,\"*return*\" + \"*-2*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "elseif (wildcard(item.service,\"*return*\" + \"*medium*\") = 1) then" writeToVBCode)
(write-line "item.speclock = false" writeToVBCode)
(write-line "item.gaugelock = false" writeToVBCode)
(write-line "item.specification = \"-3''\"" writeToVBCode)
(write-line "item.speclock = true" writeToVBCode)
(write-line "item.update()" writeToVBCode)
(write-line "elseif (wildcard(item.service,\"*supply*\" + \"*+10*\") = 1) then" writeToVBCode)
(write-line "item.speclock = false" writeToVBCode)
(write-line "item.gaugelock = false" writeToVBCode)
(write-line "item.specification = \"+10''\"" writeToVBCode)
(write-line "item.speclock = true" writeToVBCode)
(write-line "item.update()" writeToVBCode)
(write-line "elseif (wildcard(item.service,\"*supply*\" + \"*+6*\") = 1) then" writeToVBCode)
(write-line "item.speclock = false" writeToVBCode)
(write-line "item.gaugelock = false" writeToVBCode)
(write-line "item.specification = \"+6''\"" writeToVBCode)
(write-line "item.speclock = true" writeToVBCode)
(write-line "item.update()" writeToVBCode)
(write-line "elseif (wildcard(item.service,\"*supply*\" + \"*+4*\") = 1) then" writeToVBCode)
(write-line "item.speclock = false" writeToVBCode)
(write-line "item.gaugelock = false" writeToVBCode)
(write-line "item.specification = \"+4''\"" writeToVBCode)
(write-line "item.speclock = true" writeToVBCode)
(write-line "item.update()" writeToVBCode)
(write-line "elseif (wildcard(item.service,\"*supply*\" + \"*medium*\") = 1) then" writeToVBCode)
(write-line "item.speclock = false" writeToVBCode)
(write-line "item.gaugelock = false" writeToVBCode)
(write-line "item.specification = \"+3''\"" writeToVBCode)
(write-line "item.speclock = true" writeToVBCode)
(write-line "item.update()" writeToVBCode)
(write-line "elseif (wildcard(item.service,\"*supply*\" + \"*low*\") = 1) then" writeToVBCode)
(write-line "item.speclock = false" writeToVBCode)
(write-line "item.gaugelock = false" writeToVBCode)
(write-line "item.specification = \"+2''\"" writeToVBCode)
(write-line "item.speclock = true" writeToVBCode)
(write-line "item.update()" writeToVBCode)
(write-line "elseif (wildcard(item.service,\"*transfer*\") = 1) then" writeToVBCode)
(write-line "item.speclock = false" writeToVBCode)
(write-line "item.gaugelock = false" writeToVBCode)
(write-line "item.specification = \"-2''\"" writeToVBCode)
(write-line "item.speclock = true" writeToVBCode)
(write-line "item.update()" writeToVBCode)
(write-line "end if" writeToVBCode)
(write-line "i = i + 1" writeToVBCode)
(write-line "end while" writeToVBCode)
    (princ)
    (close writeToVBCode)
    (executescript vbCode sset)
    (terpri)(princ "-- Services and Specifications Updated")(princ)
    );progn
  );end if
(progn
  (if(>= (distof acadVersionYear) 2019)
    (progn
      (terpri)(prompt "Updating Activity Numbers and ItemCIDs for all items --")(princ)
    (while(< i limit)
    (INSIDE_LOOP_VARIABLES sset i)
    (if(or(wcmatch(strcase ItemServiceType)(strcase "*Equipment*"))
        (wcmatch(strcase ItemSourceFileName)(strcase "*Diffuser*"))
        (wcmatch(strcase ItemSourceFileName)(strcase "*Register*"))
        (wcmatch(strcase ItemSourceFileName)(strcase "*Grille*"))
        (wcmatch(strcase ItemSourceFileName)(strcase "*Titus*")))
    (setq Activity# "75")
    (if(or(wcmatch(strcase ItemServiceType)(strcase "*Fire Damper*"))
          (wcmatch(strcase ItemDescription)(strcase "*Canvas*"))
          (wcmatch(strcase ItemDescription)(strcase "*Access Door*"))
          (wcmatch(strcase ItemDescription)(strcase "*Damper Sleeve*"))
          (wcmatch(strcase ItemDescription)(strcase "*Plate*"))
          (and(wcmatch(strcase ItemSourceFileName)(strcase "*Angle*"))(not(wcmatch(strcase ItemSourceFileName)(strcase "*Rectangle*"))))
          (wcmatch(strcase ItemSourceFileName)(strcase "*Can*")))
      (setq Activity# "302")
      (if(or allSupport (wcmatch(strcase ItemServiceType)(strcase "*Hanger*")))
        (setq Activity# "303")
    (if(and(wcmatch(strcase ItemServiceType)(strcase "*Ductboard*"))
          (wcmatch(strcase ItemSourceFileName)(strcase "*Straight*")))
      (setq Activity# "304")
    (if(and(wcmatch(strcase ItemServiceType)(strcase "*Ductboard*"))
          (not(wcmatch(strcase ItemSourceFileName)(strcase "*Straight*"))))
      (setq Activity# "305")
        (if(and(not(or(wcmatch(strcase ItemService)(strcase "*Weld*"))(wcmatch(strcase ItemServiceType)(strcase "*Equipment*"))))
           (or
           (and(wcmatch(strcase ItemSourceFileName)(strcase "Straight"))
                       (or(wcmatch(strcase c1Name)(strcase "TDF*"))
                          (wcmatch(strcase c2Name)(strcase "TDF*"))
                          (wcmatch(strcase c1Name)(strcase "*JF*"))
                          (wcmatch(strcase c2Name)(strcase "*JF*")))
               (>= ItemLengthAngle 56))
           (and(wcmatch(strcase ItemSourceFileName)(strcase "Straight"))
               (or(wcmatch(strcase c1Name)(strcase "Stand S&D"))
                  (wcmatch(strcase c1Name)(strcase "Flat S&D"))
                  (wcmatch(strcase c2Name)(strcase "Stand S&D"))
                  (wcmatch(strcase c2Name)(strcase "Flat S&D"))
                  (wcmatch(strcase c1Name)(strcase "*S&D*"))
                  (wcmatch(strcase c2Name)(strcase "*S&D*")))
               (>= ItemLengthAngle 59))
          ))
          (setq Activity# "310")
          (if(wcmatch(strcase ItemSourceFileName)(strcase "*SPIRAL"))
            (setq Activity# "312")
            (if(and(not(or(wcmatch(strcase ItemService)(strcase "*Weld*"))(wcmatch(strcase ItemServiceType)(strcase "*Equipment*"))))
               (or
               (wcmatch(strcase ItemSourceFileName)(strcase "*Pipe*"))
               (and
               (= ItemLengthAngle 18)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*8/6/6*"))
                  (wcmatch(strcase ItemDescription)(strcase "*10/8/6*"))
                  (wcmatch(strcase ItemDescription)(strcase "*10/8/8*"))
                  (wcmatch(strcase ItemDescription)(strcase "*12/8/6*"))
                  (wcmatch(strcase ItemDescription)(strcase "*12/8/8*"))
                  (wcmatch(strcase ItemDescription)(strcase "*12/10/6*"))
                  (wcmatch(strcase ItemDescription)(strcase "*12/10/8*"))
                  (wcmatch(strcase ItemDescription)(strcase "*12/10/10*"))
                  (wcmatch(strcase ItemDescription)(strcase "*14/10/8*"))
                  (wcmatch(strcase ItemDescription)(strcase "*14/10/10*"))
                  (wcmatch(strcase ItemDescription)(strcase "*14/12/6*"))
                  (wcmatch(strcase ItemDescription)(strcase "*14/12/8*"))
                  (wcmatch(strcase ItemDescription)(strcase "*14/12/10*"))
                  (wcmatch(strcase ItemDescription)(strcase "*16/10/10*"))
                  (wcmatch(strcase ItemDescription)(strcase "*16/12/8*"))
                  (wcmatch(strcase ItemDescription)(strcase "*16/12/10*"))
                  (wcmatch(strcase ItemDescription)(strcase "*16/14/8*"))
                  (wcmatch(strcase ItemDescription)(strcase "*16/14/10*")))
               )
               (and
               (= ItemLengthAngle 20)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*14/12/12*"))
                  (wcmatch(strcase ItemDescription)(strcase "*16/12/12*"))
                  (wcmatch(strcase ItemDescription)(strcase "*16/14/12*")))
               )
               (and
               (= ItemLengthAngle 30)
               (or(wcmatch(strcase ItemSourceFileName)(strcase "*Wye*"))
                  (wcmatch(strcase ItemSourceFileName)(strcase "*No Dampers*"))
                  (wcmatch(strcase ItemSourceFileName)(strcase "*KS7L*"))
                  (wcmatch(strcase ItemSourceFileName)(strcase "*3-8 Rod*")))
               (not(wcmatch(strcase ItemSourceFileName)(strcase "*Lateral 45*")))
               (not(wcmatch(strcase ItemSourceFileName)(strcase "*Conical Cross*")))
               (not(wcmatch(strcase ItemSourceFileName)(strcase "*Conical Tee*")))
               (not(wcmatch ItemCID "807"))
               (not(wcmatch ItemCID "812"))
               (or(wcmatch(strcase ItemDescription)(strcase "*16/14/14*"))
                  (wcmatch(strcase ItemDescription)(strcase "*18/14/14*")))
               )
               (and
               (= ItemLengthAngle 18)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*6/6/6*"))
               (wcmatch(strcase ItemDescription)(strcase "*8/8/8*"))
               (wcmatch(strcase ItemDescription)(strcase "*10/10/6*"))
               (wcmatch(strcase ItemDescription)(strcase "*10/10/8*"))
               (wcmatch(strcase ItemDescription)(strcase "*10/10/10*"))
               (wcmatch(strcase ItemDescription)(strcase "*12/12/6*"))
               (wcmatch(strcase ItemDescription)(strcase "*12/12/8*"))
               (wcmatch(strcase ItemDescription)(strcase "*12/12/10*"))
               (wcmatch(strcase ItemDescription)(strcase "*14/14/6*"))
               (wcmatch(strcase ItemDescription)(strcase "*14/14/8*"))
               (wcmatch(strcase ItemDescription)(strcase "*14/14/10*"))
               (wcmatch(strcase ItemDescription)(strcase "*16/16/8*")))
               )
               (and
               (= ItemLengthAngle 20)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*12/12/12*"))
               (wcmatch(strcase ItemDescription)(strcase "*14/14/12*")))
               )
               (and
               (= ItemLengthAngle 30)
               (or(wcmatch(strcase ItemSourceFileName)(strcase "*Lateral 45*"))
               (wcmatch(strcase ItemSourceFileName)(strcase "*No Dampers*"))
               (wcmatch(strcase ItemSourceFileName)(strcase "*KS7L*"))
               (wcmatch(strcase ItemSourceFileName)(strcase "*3-8 Rod*")))
               (not(wcmatch(strcase ItemSourceFileName)(strcase "*Wye*")))
               (not(wcmatch(strcase ItemSourceFileName)(strcase "*Conical Cross*")))
               (not(wcmatch(strcase ItemSourceFileName)(strcase "*Conical Tee*")))
               (not(wcmatch ItemCID "53"))
               (not(wcmatch ItemCID "812"))
               (or(wcmatch(strcase ItemDescription)(strcase "*14/14/14*")))
               )
               (and
               (wcmatch ItemCID "60")
               (wcmatch(strcase ItemSourceFileName)(strcase "*Cap*"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (wcmatch ItemCID "60")
               (wcmatch(strcase ItemSourceFileName)(strcase "*End Cap*"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (wcmatch ItemCID "1112")
               (wcmatch(strcase ItemDescription)(strcase "*3\" Collar*"))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*"))
                  (wcmatch(strcase ItemDescription)(strcase "*20\"*")))
               )
               (and
               (wcmatch ItemCID "1112")
               (wcmatch(strcase ItemDescription)(strcase "*Spin-in*"))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*")))
               )
               (and
                  (wcmatch(strcase ItemDescription)(strcase "*6\" Long Taper*"))
               (or(wcmatch(strcase ItemDescription)(strcase "*7-5*"))
                  (wcmatch(strcase ItemDescription)(strcase "*8-6*"))
                  (wcmatch(strcase ItemDescription)(strcase "*9-7*"))
                  (wcmatch(strcase ItemDescription)(strcase "*10-8*"))
                  (wcmatch(strcase ItemDescription)(strcase "*10-9*"))
                  (wcmatch(strcase ItemDescription)(strcase "*12-10*"))
                  (wcmatch(strcase ItemDescription)(strcase "*14-12*"))
                  (wcmatch(strcase ItemDescription)(strcase "*16-14*"))
                  (wcmatch(strcase ItemDescription)(strcase "*18-16*")))
               )
               (and
                  (wcmatch(strcase ItemDescription)(strcase "*12\" Long Taper*"))
               (or(wcmatch(strcase ItemDescription)(strcase "*10-6*"))
                  (wcmatch(strcase ItemDescription)(strcase "*12-8*"))
                  (wcmatch(strcase ItemDescription)(strcase "*14-10*"))
                  (wcmatch(strcase ItemDescription)(strcase "*16-12*"))
                  (wcmatch(strcase ItemDescription)(strcase "*18-14*"))
                  (wcmatch(strcase ItemDescription)(strcase "*8-5*"))
                  (wcmatch(strcase ItemDescription)(strcase "*7-6*"))
                  (wcmatch(strcase ItemDescription)(strcase "*9-6*"))
                  (wcmatch(strcase ItemDescription)(strcase "*8-7*"))
                  (wcmatch(strcase ItemDescription)(strcase "*9-7*"))
                  (wcmatch(strcase ItemDescription)(strcase "*10-7*"))
                  (wcmatch(strcase ItemDescription)(strcase "*12-7*"))
                  (wcmatch(strcase ItemDescription)(strcase "*10-9*"))
                  (wcmatch(strcase ItemDescription)(strcase "*12-6*"))
                  (wcmatch(strcase ItemDescription)(strcase "*12-10*"))
                  (wcmatch(strcase ItemDescription)(strcase "*18-10*")))
               )
               (and
                  (wcmatch(strcase ItemDescription)(strcase "*18\" Long Taper*"))
               (or(wcmatch(strcase ItemDescription)(strcase "*12-6*"))
                  (wcmatch(strcase ItemDescription)(strcase "*14-6*"))
                  (wcmatch(strcase ItemDescription)(strcase "*12-8*"))
                  (wcmatch(strcase ItemDescription)(strcase "*14-8*"))
                  (wcmatch(strcase ItemDescription)(strcase "*16-8*"))
                  (wcmatch(strcase ItemDescription)(strcase "*16-12*"))
                  (wcmatch(strcase ItemDescription)(strcase "*18-12*"))
                  (wcmatch(strcase ItemDescription)(strcase "*16-14*"))
                  (wcmatch(strcase ItemDescription)(strcase "*18-14*"))
                  (wcmatch(strcase ItemDescription)(strcase "*20-14*"))
                  (wcmatch(strcase ItemDescription)(strcase "*18-16*"))
                  (wcmatch(strcase ItemDescription)(strcase "*20-18*"))
                  (wcmatch(strcase ItemDescription)(strcase "*6-5*"))
                  (wcmatch(strcase ItemDescription)(strcase "*7-6*"))
                  (wcmatch(strcase ItemDescription)(strcase "*8-7*"))
                  (wcmatch(strcase ItemDescription)(strcase "*9-8*"))
                  (wcmatch(strcase ItemDescription)(strcase "*10-9*"))
                  (wcmatch(strcase ItemDescription)(strcase "*9-6*"))
                  (wcmatch(strcase ItemDescription)(strcase "*9-7*"))
                  (wcmatch(strcase ItemDescription)(strcase "*10-7*"))
                  (wcmatch(strcase ItemDescription)(strcase "*12-7*"))
                  (wcmatch(strcase ItemDescription)(strcase "*14-7*"))
                  (wcmatch(strcase ItemDescription)(strcase "*12-9*"))
                  (wcmatch(strcase ItemDescription)(strcase "*14-9*")))
               )
               (and
               (or(wcmatch(strcase ItemSourceFileName)(strcase "*45Deg on Rd Saddle*"))
                  (wcmatch(strcase ItemDescription)(strcase "*45 Deg Sad*"))
                  (wcmatch ItemCID "875"))
               (or(wcmatch(strcase ItemDescription)(strcase "*6\" on 6\"*"))
                  (wcmatch(strcase ItemDescription)(strcase "*6 on 6*"))
                  (wcmatch(strcase ItemDescription)(strcase "*6\" on 8\"*"))
                  (wcmatch(strcase ItemDescription)(strcase "*6 on 8*"))
                  (wcmatch(strcase ItemDescription)(strcase "*6\" on 10\"*"))
                  (wcmatch(strcase ItemDescription)(strcase "*6 on 10*"))
                  (wcmatch(strcase ItemDescription)(strcase "*6\" on 12\"*"))
                  (wcmatch(strcase ItemDescription)(strcase "*6 on 12*"))
                  (wcmatch(strcase ItemDescription)(strcase "*6\" on 14\"*"))
                  (wcmatch(strcase ItemDescription)(strcase "*6 on 14*"))
                  (wcmatch(strcase ItemDescription)(strcase "*6\" on 16\"*"))
                  (wcmatch(strcase ItemDescription)(strcase "*6 on 16*"))
                  (wcmatch(strcase ItemDescription)(strcase "*6\" on 18\"*"))
                  (wcmatch(strcase ItemDescription)(strcase "*6 on 18*"))
                  (wcmatch(strcase ItemDescription)(strcase "*8\" on 8\"*"))
                  (wcmatch(strcase ItemDescription)(strcase "*8 on 8*"))
                  (wcmatch(strcase ItemDescription)(strcase "*8\" on 10\"*"))
                  (wcmatch(strcase ItemDescription)(strcase "*8 on 10*"))
                  (wcmatch(strcase ItemDescription)(strcase "*8\" on 12\"*"))
                  (wcmatch(strcase ItemDescription)(strcase "*8 on 12*"))
                  (wcmatch(strcase ItemDescription)(strcase "*8\" on 14\"*"))
                  (wcmatch(strcase ItemDescription)(strcase "*8 on 14*"))
                  (wcmatch(strcase ItemDescription)(strcase "*8\" on 16\"*"))
                  (wcmatch(strcase ItemDescription)(strcase "*8 on 16*"))
                  (wcmatch(strcase ItemDescription)(strcase "*8\" on 18\"*"))
                  (wcmatch(strcase ItemDescription)(strcase "*8 on 18*"))
                  (wcmatch(strcase ItemDescription)(strcase "*10\" on 10\"*"))
                  (wcmatch(strcase ItemDescription)(strcase "*10 on 10*"))
                  (wcmatch(strcase ItemDescription)(strcase "*10\" on 12\"*"))
                  (wcmatch(strcase ItemDescription)(strcase "*10 on 12*"))
                  (wcmatch(strcase ItemDescription)(strcase "*10\" on 14\"*"))
                  (wcmatch(strcase ItemDescription)(strcase "*10 on 14*"))
                  (wcmatch(strcase ItemDescription)(strcase "*10\" on 16\"*"))
                  (wcmatch(strcase ItemDescription)(strcase "*10 on 16*"))
                  (wcmatch(strcase ItemDescription)(strcase "*10\" on 18\"*"))
                  (wcmatch(strcase ItemDescription)(strcase "*10 on 18*"))
                  (wcmatch(strcase ItemDescription)(strcase "*10\" on 20\"*"))
                  (wcmatch(strcase ItemDescription)(strcase "*10 on 20*"))
                  (wcmatch(strcase ItemDescription)(strcase "*14\" on 14\"*"))
                  (wcmatch(strcase ItemDescription)(strcase "*14 on 14*"))
                  (wcmatch(strcase ItemDescription)(strcase "*14\" on 16\"*"))
                  (wcmatch(strcase ItemDescription)(strcase "*14 on 16*")))
               )
               (and
               (or(wcmatch(strcase ItemSourceFileName)(strcase "*45Deg Flat Saddle*"))
                  (wcmatch(strcase ItemDescription)(strcase "*45D Flat*"))
                  (wcmatch ItemCID "16"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*")))
               )
               (and
               (or(wcmatch(strcase ItemSourceFileName)(strcase "*Rd on Rd Conical*"))
                  (wcmatch(strcase ItemDescription)(strcase "*#8 *"))
                  (wcmatch ItemCID "751"))
               (or(wcmatch(strcase ItemDescription)(strcase "*6\" on 8\"*"))
                  (wcmatch(strcase ItemDescription)(strcase "*6 on 8*"))
                  (wcmatch(strcase ItemDescription)(strcase "*6\" on 10\"*"))
                  (wcmatch(strcase ItemDescription)(strcase "*6 on 10*"))
                  (wcmatch(strcase ItemDescription)(strcase "*6\" on 12\"*"))
                  (wcmatch(strcase ItemDescription)(strcase "*6 on 12*"))
                  (wcmatch(strcase ItemDescription)(strcase "*6\" on 14\"*"))
                  (wcmatch(strcase ItemDescription)(strcase "*6 on 14*"))
                  (wcmatch(strcase ItemDescription)(strcase "*6\" on 16\"*"))
                  (wcmatch(strcase ItemDescription)(strcase "*6 on 16*"))
                  (wcmatch(strcase ItemDescription)(strcase "*6\" on 18\"*"))
                  (wcmatch(strcase ItemDescription)(strcase "*6 on 18*"))
                  (wcmatch(strcase ItemDescription)(strcase "*6\" on 20\"*"))
                  (wcmatch(strcase ItemDescription)(strcase "*6 on 20*"))
                  (wcmatch(strcase ItemDescription)(strcase "*8\" on 10\"*"))
                  (wcmatch(strcase ItemDescription)(strcase "*8 on 10*"))
                  (wcmatch(strcase ItemDescription)(strcase "*8\" on 12\"*"))
                  (wcmatch(strcase ItemDescription)(strcase "*8 on 12*"))
                  (wcmatch(strcase ItemDescription)(strcase "*8\" on 14\"*"))
                  (wcmatch(strcase ItemDescription)(strcase "*8 on 14*"))
                  (wcmatch(strcase ItemDescription)(strcase "*8\" on 16\"*"))
                  (wcmatch(strcase ItemDescription)(strcase "*8 on 16*"))
                  (wcmatch(strcase ItemDescription)(strcase "*8\" on 18\"*"))
                  (wcmatch(strcase ItemDescription)(strcase "*8 on 18*"))
                  (wcmatch(strcase ItemDescription)(strcase "*10\" on 12\"*"))
                  (wcmatch(strcase ItemDescription)(strcase "*10 on 12*"))
                  (wcmatch(strcase ItemDescription)(strcase "*10\" on 14\"*"))
                  (wcmatch(strcase ItemDescription)(strcase "*10 on 14*"))
                  (wcmatch(strcase ItemDescription)(strcase "*10\" on 16\"*"))
                  (wcmatch(strcase ItemDescription)(strcase "*10 on 16*"))
                  (wcmatch(strcase ItemDescription)(strcase "*10\" on 18\"*"))
                  (wcmatch(strcase ItemDescription)(strcase "*10 on 18*"))
                  (wcmatch(strcase ItemDescription)(strcase "*12\" on 14\"*"))
                  (wcmatch(strcase ItemDescription)(strcase "*12 on 14*"))
                  (wcmatch(strcase ItemDescription)(strcase "*12\" on 16\"*"))
                  (wcmatch(strcase ItemDescription)(strcase "*12 on 16*"))
                  (wcmatch(strcase ItemDescription)(strcase "*12\" on 18\"*"))
                  (wcmatch(strcase ItemDescription)(strcase "*12 on 18*"))
                  (wcmatch(strcase ItemDescription)(strcase "*12\" on 20\"*"))
                  (wcmatch(strcase ItemDescription)(strcase "*12 on 20*"))
                  (wcmatch(strcase ItemDescription)(strcase "*14\" on 16\"*"))
                  (wcmatch(strcase ItemDescription)(strcase "*14 on 16*"))
                  (wcmatch(strcase ItemDescription)(strcase "*14\" on 18\"*"))
                  (wcmatch(strcase ItemDescription)(strcase "*14 on 18*")))
               )
               (and
               (or(wcmatch(strcase ItemSourceFileName)(strcase "*Round Access Door*"))
                  (wcmatch(strcase ItemSourceFileName)(strcase "*#7 Access Door*")))
               (or(wcmatch(strcase ItemDescription)(strcase "*6\"*"))
                  (wcmatch(strcase ItemDescription)(strcase "*8\"*"))
                  (wcmatch(strcase ItemDescription)(strcase "*10\"*"))
                  (wcmatch(strcase ItemDescription)(strcase "*12\"*"))
                  (wcmatch(strcase ItemDescription)(strcase "*14\"*")))
               )
               (and
               (or(wcmatch(strcase ItemSourceFileName)(strcase "*Conical Flat Tap*"))
                  (wcmatch(strcase ItemSourceFileName)(strcase "*Flat Conical 1\" Flg*"))
                  (wcmatch ItemCID "345"))
               (or(wcmatch(strcase ItemDescription)(strcase "*5\"*"))
                  (wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(and(wcmatch ItemCID "51")(wcmatch(strcase ItemSourceFileName)(strcase "*6\" Start Collar wFlg*"))(wcmatch(strcase ItemDescription)(strcase "*for Damper*")))
                  (and(wcmatch ItemCID "51")(wcmatch(strcase ItemDescription)(strcase "*Damper*"))))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(and(wcmatch ItemCID "51")(wcmatch(strcase ItemSourceFileName)(strcase "*6\" Start Collar wFlg*"))(not(wcmatch(strcase ItemDescription)(strcase "*for Damper*"))))
                  (and(wcmatch ItemCID "51")(not(wcmatch(strcase ItemDescription)(strcase "*Damper*")))))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*")))
               )
               (and
               (or(wcmatch(strcase ItemSourceFileName)(strcase "Coupling")))
               (or(wcmatch(strcase ItemDescription)(strcase "*6\"*"))
                  (wcmatch(strcase ItemDescription)(strcase "*7\"*"))
                  (wcmatch(strcase ItemDescription)(strcase "*8\"*"))
                  (wcmatch(strcase ItemDescription)(strcase "*9\"*"))
                  (wcmatch(strcase ItemDescription)(strcase "*10\"*"))
                  (wcmatch(strcase ItemDescription)(strcase "*12\"*"))
                  (wcmatch(strcase ItemDescription)(strcase "*14\"*"))
                  (wcmatch(strcase ItemDescription)(strcase "*16\"*"))
                  (wcmatch(strcase ItemDescription)(strcase "*18\"*")))
               )
               (and
               (or(wcmatch ItemCID "522")
                  (wcmatch(strcase ItemSourceFileName)(strcase "#2 Coupling")))
               (or(= dim1 6)
                  (= dim1 7)
                  (= dim1 8)
                  (= dim1 9)
                  (= dim1 10)
                  (= dim1 12)
                  (= dim1 14)
                  (= dim1 16)
                  (= dim1 18)
                  (= dim1 20))
               )
               )
               )
              (setq Activity# "316")
            (if(and(not(or(wcmatch(strcase ItemService)(strcase "*Weld*"))(wcmatch(strcase ItemServiceType)(strcase "*Equipment*"))))
               (or
                 (or(wcmatch(strcase ItemSourceFileName)(strcase "*Conical Cross*"))
                    (wcmatch(strcase ItemSourceFileName)(strcase "*Conical Tee*"))
                    (wcmatch(strcase ItemSourceFileName)(strcase "*90 Adj.*"))
                    (wcmatch(strcase ItemSourceFileName)(strcase "*45 Adj.*"))
                    (wcmatch(strcase ItemSourceFileName)(strcase "*Misc. Elbow*"))
                    (wcmatch(strcase ItemSourceFileName)(strcase "*Welded Elbow*"))
                    (wcmatch(strcase ItemSourceFileName)(strcase "*90Deg Adj.*"))
                    (wcmatch(strcase ItemSourceFileName)(strcase "*45Deg Adj.*"))
                    (wcmatch(strcase ItemSourceFileName)(strcase "Misc. Adj. Elbow*"))
                    (wcmatch(strcase ItemSourceFileName)(strcase "Misc. Adjustable Elbow*"))
                    (wcmatch(strcase ItemSourceFileName)(strcase "Misc. El*"))
                    (wcmatch(strcase ItemSourceFileName)(strcase "*Shoe Barrel*"))
                    (wcmatch(strcase ItemSourceFileName)(strcase "*Shoe Saddle*"))
                    (wcmatch(strcase ItemSourceFileName)(strcase "*Mitered Offset Fixed*"))
                    (wcmatch(strcase ItemSourceFileName)(strcase "*Deflector Hood*"))
                    (wcmatch(strcase ItemSourceFileName)(strcase "*FULL RAD.*"))
                    (wcmatch(strcase ItemSourceFileName)(strcase "*HALF RAD.*"))
                    (wcmatch(strcase ItemSourceFileName)(strcase "*Pancake*"))
                    (wcmatch(strcase ItemSourceFileName)(strcase "*Flex*"))
                    (wcmatch(strcase ItemSourceFileName)(strcase "*Welded Pipe*"))
                    (wcmatch(strcase ItemDescription)(strcase "* CROSS*"))
                 )
                 (and
                 (= ItemLengthAngle 18)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*8/6/6*"))
                    (wcmatch(strcase ItemDescription)(strcase "*10/8/6*"))
                    (wcmatch(strcase ItemDescription)(strcase "*10/8/8*"))
                    (wcmatch(strcase ItemDescription)(strcase "*12/8/6*"))
                    (wcmatch(strcase ItemDescription)(strcase "*12/8/8*"))
                    (wcmatch(strcase ItemDescription)(strcase "*12/10/6*"))
                    (wcmatch(strcase ItemDescription)(strcase "*12/10/8*"))
                    (wcmatch(strcase ItemDescription)(strcase "*12/10/10*"))
                    (wcmatch(strcase ItemDescription)(strcase "*14/10/8*"))
                    (wcmatch(strcase ItemDescription)(strcase "*14/10/10*"))
                    (wcmatch(strcase ItemDescription)(strcase "*14/12/6*"))
                    (wcmatch(strcase ItemDescription)(strcase "*14/12/8*"))
                    (wcmatch(strcase ItemDescription)(strcase "*14/12/10*"))
                    (wcmatch(strcase ItemDescription)(strcase "*16/10/10*"))
                    (wcmatch(strcase ItemDescription)(strcase "*16/12/8*"))
                    (wcmatch(strcase ItemDescription)(strcase "*16/12/10*"))
                    (wcmatch(strcase ItemDescription)(strcase "*16/14/8*"))
                    (wcmatch(strcase ItemDescription)(strcase "*16/14/10*"))))
                 )
                 (and
                 (= ItemLengthAngle 20)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*14/12/12*"))
                    (wcmatch(strcase ItemDescription)(strcase "*16/12/12*"))
                    (wcmatch(strcase ItemDescription)(strcase "*16/14/12*"))))
                 )
                 (and
                 (= ItemLengthAngle 30)
                 (or(wcmatch(strcase ItemSourceFileName)(strcase "*Wye*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Lateral 45*")))
                 (not(wcmatch(strcase ItemSourceFileName)(strcase "*Conical Cross*")))
                 (not(wcmatch(strcase ItemSourceFileName)(strcase "*Conical Tee*")))
                 (not(wcmatch ItemCID "807"))
                 (not(wcmatch ItemCID "812"))
                 (not(or(wcmatch(strcase ItemDescription)(strcase "*16/14/14*"))
                    (wcmatch(strcase ItemDescription)(strcase "*18/14/14*"))))
                 )
                 (and
                 (= ItemLengthAngle 18)
                 (or(wcmatch(strcase ItemSourceFileName)(strcase "*Lateral 45*"))
                    (wcmatch(strcase ItemSourceFileName)(strcase "*No Dampers*"))
                    (wcmatch(strcase ItemSourceFileName)(strcase "*KS7L*"))
                    (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*6/6/6*"))
                 (wcmatch(strcase ItemDescription)(strcase "*8/8/8*"))
                 (wcmatch(strcase ItemDescription)(strcase "*10/10/6*"))
                 (wcmatch(strcase ItemDescription)(strcase "*10/10/8*"))
                 (wcmatch(strcase ItemDescription)(strcase "*10/10/10*"))
                 (wcmatch(strcase ItemDescription)(strcase "*12/12/6*"))
                 (wcmatch(strcase ItemDescription)(strcase "*12/12/8*"))
                 (wcmatch(strcase ItemDescription)(strcase "*12/12/10*"))
                 (wcmatch(strcase ItemDescription)(strcase "*14/14/6*"))
                 (wcmatch(strcase ItemDescription)(strcase "*14/14/8*"))
                 (wcmatch(strcase ItemDescription)(strcase "*14/14/10*"))
                 (wcmatch(strcase ItemDescription)(strcase "*16/16/8*"))))
                 )
                 (and
                 (= ItemLengthAngle 20)
                 (or(wcmatch(strcase ItemSourceFileName)(strcase "*Lateral 45*"))
                 (wcmatch(strcase ItemSourceFileName)(strcase "*No Dampers*"))
                 (wcmatch(strcase ItemSourceFileName)(strcase "*KS7L*"))
                 (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*12/12/12*"))
                 (wcmatch(strcase ItemDescription)(strcase "*14/14/12*"))))
                 )
                 (and
                 (= ItemLengthAngle 30)
                 (or(wcmatch(strcase ItemSourceFileName)(strcase "*Lateral 45*"))
                 (wcmatch(strcase ItemSourceFileName)(strcase "*No Dampers*"))
                 (wcmatch(strcase ItemSourceFileName)(strcase "*KS7L*"))
                 (wcmatch(strcase ItemSourceFileName)(strcase "*3-8 Rod*")))
                 (not(wcmatch(strcase ItemSourceFileName)(strcase "*Wye*")))
                 (not(wcmatch(strcase ItemSourceFileName)(strcase "*Conical Cross*")))
                 (not(wcmatch(strcase ItemSourceFileName)(strcase "*Conical Tee*")))
                 (not(wcmatch ItemCID "53"))
                 (not(wcmatch ItemCID "812"))
                 (not(or(wcmatch(strcase ItemDescription)(strcase "*14/14/14*"))))
                 )
                 (and(wcmatch ItemCID "60")
                     (wcmatch(strcase ItemSourceFileName)(strcase "*Cap*"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and(wcmatch ItemCID "60")
                     (wcmatch(strcase ItemSourceFileName)(strcase "*End Cap*"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and(wcmatch ItemCID "1112")
                     (wcmatch(strcase ItemDescription)(strcase "*3\" Collar*"))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))
                    (wcmatch(strcase ItemDescription)(strcase "*20\"*"))))
                 )
                 (and(wcmatch ItemCID "1112")
                     (wcmatch(strcase ItemDescription)(strcase "*Spin-in*"))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))))
                 )
                 (and(wcmatch(strcase ItemDescription)(strcase "*6\" Long Taper*"))
                 (not(or(wcmatch(strcase ItemDescription)(strcase "*7-5*"))
                    (wcmatch(strcase ItemDescription)(strcase "*8-6*"))
                    (wcmatch(strcase ItemDescription)(strcase "*9-7*"))
                    (wcmatch(strcase ItemDescription)(strcase "*10-8*"))
                    (wcmatch(strcase ItemDescription)(strcase "*10-9*"))
                    (wcmatch(strcase ItemDescription)(strcase "*12-10*"))
                    (wcmatch(strcase ItemDescription)(strcase "*14-12*"))
                    (wcmatch(strcase ItemDescription)(strcase "*16-14*"))
                    (wcmatch(strcase ItemDescription)(strcase "*18-16*"))))
                 )
                 (and(wcmatch(strcase ItemDescription)(strcase "*12\" Long Taper*"))
                 (not(or(wcmatch(strcase ItemDescription)(strcase "*10-6*"))
                    (wcmatch(strcase ItemDescription)(strcase "*12-8*"))
                    (wcmatch(strcase ItemDescription)(strcase "*14-10*"))
                    (wcmatch(strcase ItemDescription)(strcase "*16-12*"))
                    (wcmatch(strcase ItemDescription)(strcase "*18-14*"))
                    (wcmatch(strcase ItemDescription)(strcase "*8-5*"))
                    (wcmatch(strcase ItemDescription)(strcase "*7-6*"))
                    (wcmatch(strcase ItemDescription)(strcase "*9-6*"))
                    (wcmatch(strcase ItemDescription)(strcase "*8-7*"))
                    (wcmatch(strcase ItemDescription)(strcase "*9-7*"))
                    (wcmatch(strcase ItemDescription)(strcase "*10-7*"))
                    (wcmatch(strcase ItemDescription)(strcase "*12-7*"))
                    (wcmatch(strcase ItemDescription)(strcase "*10-9*"))
                    (wcmatch(strcase ItemDescription)(strcase "*12-6*"))
                    (wcmatch(strcase ItemDescription)(strcase "*12-10*"))
                    (wcmatch(strcase ItemDescription)(strcase "*18-10*"))))
                 )
                 (and(wcmatch(strcase ItemDescription)(strcase "*18\" Long Taper*"))
                 (not(or(wcmatch(strcase ItemDescription)(strcase "*12-6*"))
                    (wcmatch(strcase ItemDescription)(strcase "*14-6*"))
                    (wcmatch(strcase ItemDescription)(strcase "*12-8*"))
                    (wcmatch(strcase ItemDescription)(strcase "*14-8*"))
                    (wcmatch(strcase ItemDescription)(strcase "*16-8*"))
                    (wcmatch(strcase ItemDescription)(strcase "*16-12*"))
                    (wcmatch(strcase ItemDescription)(strcase "*18-12*"))
                    (wcmatch(strcase ItemDescription)(strcase "*16-14*"))
                    (wcmatch(strcase ItemDescription)(strcase "*18-14*"))
                    (wcmatch(strcase ItemDescription)(strcase "*20-14*"))
                    (wcmatch(strcase ItemDescription)(strcase "*18-16*"))
                    (wcmatch(strcase ItemDescription)(strcase "*20-18*"))
                    (wcmatch(strcase ItemDescription)(strcase "*6-5*"))
                    (wcmatch(strcase ItemDescription)(strcase "*7-6*"))
                    (wcmatch(strcase ItemDescription)(strcase "*8-7*"))
                    (wcmatch(strcase ItemDescription)(strcase "*9-8*"))
                    (wcmatch(strcase ItemDescription)(strcase "*10-9*"))
                    (wcmatch(strcase ItemDescription)(strcase "*9-6*"))
                    (wcmatch(strcase ItemDescription)(strcase "*9-7*"))
                    (wcmatch(strcase ItemDescription)(strcase "*10-7*"))
                    (wcmatch(strcase ItemDescription)(strcase "*12-7*"))
                    (wcmatch(strcase ItemDescription)(strcase "*14-7*"))
                    (wcmatch(strcase ItemDescription)(strcase "*12-9*"))
                    (wcmatch(strcase ItemDescription)(strcase "*14-9*"))))
                 )
                 (and
                 (or(wcmatch(strcase ItemSourceFileName)(strcase "*45Deg on Rd Saddle*"))
                    (wcmatch(strcase ItemDescription)(strcase "*45 Deg Sad*"))
                    (wcmatch ItemCID "875"))
                 (not(or(wcmatch(strcase ItemDescription)(strcase "*6\" on 6\"*"))
                    (wcmatch(strcase ItemDescription)(strcase "*6 on 6*"))
                    (wcmatch(strcase ItemDescription)(strcase "*6\" on 8\"*"))
                    (wcmatch(strcase ItemDescription)(strcase "*6 on 8*"))
                    (wcmatch(strcase ItemDescription)(strcase "*6\" on 10\"*"))
                    (wcmatch(strcase ItemDescription)(strcase "*6 on 10*"))
                    (wcmatch(strcase ItemDescription)(strcase "*6\" on 12\"*"))
                    (wcmatch(strcase ItemDescription)(strcase "*6 on 12*"))
                    (wcmatch(strcase ItemDescription)(strcase "*6\" on 14\"*"))
                    (wcmatch(strcase ItemDescription)(strcase "*6 on 14*"))
                    (wcmatch(strcase ItemDescription)(strcase "*6\" on 16\"*"))
                    (wcmatch(strcase ItemDescription)(strcase "*6 on 16*"))
                    (wcmatch(strcase ItemDescription)(strcase "*6\" on 18\"*"))
                    (wcmatch(strcase ItemDescription)(strcase "*6 on 18*"))
                    (wcmatch(strcase ItemDescription)(strcase "*8\" on 8\"*"))
                    (wcmatch(strcase ItemDescription)(strcase "*8 on 8*"))
                    (wcmatch(strcase ItemDescription)(strcase "*8\" on 10\"*"))
                    (wcmatch(strcase ItemDescription)(strcase "*8 on 10*"))
                    (wcmatch(strcase ItemDescription)(strcase "*8\" on 12\"*"))
                    (wcmatch(strcase ItemDescription)(strcase "*8 on 12*"))
                    (wcmatch(strcase ItemDescription)(strcase "*8\" on 14\"*"))
                    (wcmatch(strcase ItemDescription)(strcase "*8 on 14*"))
                    (wcmatch(strcase ItemDescription)(strcase "*8\" on 16\"*"))
                    (wcmatch(strcase ItemDescription)(strcase "*8 on 16*"))
                    (wcmatch(strcase ItemDescription)(strcase "*8\" on 18\"*"))
                    (wcmatch(strcase ItemDescription)(strcase "*8 on 18*"))
                    (wcmatch(strcase ItemDescription)(strcase "*10\" on 10\"*"))
                    (wcmatch(strcase ItemDescription)(strcase "*10 on 10*"))
                    (wcmatch(strcase ItemDescription)(strcase "*10\" on 12\"*"))
                    (wcmatch(strcase ItemDescription)(strcase "*10 on 12*"))
                    (wcmatch(strcase ItemDescription)(strcase "*10\" on 14\"*"))
                    (wcmatch(strcase ItemDescription)(strcase "*10 on 14*"))
                    (wcmatch(strcase ItemDescription)(strcase "*10\" on 16\"*"))
                    (wcmatch(strcase ItemDescription)(strcase "*10 on 16*"))
                    (wcmatch(strcase ItemDescription)(strcase "*10\" on 18\"*"))
                    (wcmatch(strcase ItemDescription)(strcase "*10 on 18*"))
                    (wcmatch(strcase ItemDescription)(strcase "*10\" on 20\"*"))
                    (wcmatch(strcase ItemDescription)(strcase "*10 on 20*"))
                    (wcmatch(strcase ItemDescription)(strcase "*14\" on 14\"*"))
                    (wcmatch(strcase ItemDescription)(strcase "*14 on 14*"))
                    (wcmatch(strcase ItemDescription)(strcase "*14\" on 16\"*"))
                    (wcmatch(strcase ItemDescription)(strcase "*14 on 16*"))))
                 )
                 (and
                 (or(wcmatch(strcase ItemSourceFileName)(strcase "*45Deg Flat Saddle*"))
                    (wcmatch(strcase ItemDescription)(strcase "*45D Flat*"))
                    (wcmatch ItemCID "16"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))))
                 )
                 (and
                 (or(wcmatch(strcase ItemSourceFileName)(strcase "*Rd on Rd Conical*"))
                    (wcmatch(strcase ItemDescription)(strcase "*#8 *"))
                    (wcmatch ItemCID "751"))
                 (not(or(wcmatch(strcase ItemDescription)(strcase "*6\" on 8\"*"))
                    (wcmatch(strcase ItemDescription)(strcase "*6 on 8*"))
                    (wcmatch(strcase ItemDescription)(strcase "*6\" on 10\"*"))
                    (wcmatch(strcase ItemDescription)(strcase "*6 on 10*"))
                    (wcmatch(strcase ItemDescription)(strcase "*6\" on 12\"*"))
                    (wcmatch(strcase ItemDescription)(strcase "*6 on 12*"))
                    (wcmatch(strcase ItemDescription)(strcase "*6\" on 14\"*"))
                    (wcmatch(strcase ItemDescription)(strcase "*6 on 14*"))
                    (wcmatch(strcase ItemDescription)(strcase "*6\" on 16\"*"))
                    (wcmatch(strcase ItemDescription)(strcase "*6 on 16*"))
                    (wcmatch(strcase ItemDescription)(strcase "*6\" on 18\"*"))
                    (wcmatch(strcase ItemDescription)(strcase "*6 on 18*"))
                    (wcmatch(strcase ItemDescription)(strcase "*6\" on 20\"*"))
                    (wcmatch(strcase ItemDescription)(strcase "*6 on 20*"))
                    (wcmatch(strcase ItemDescription)(strcase "*8\" on 10\"*"))
                    (wcmatch(strcase ItemDescription)(strcase "*8 on 10*"))
                    (wcmatch(strcase ItemDescription)(strcase "*8\" on 12\"*"))
                    (wcmatch(strcase ItemDescription)(strcase "*8 on 12*"))
                    (wcmatch(strcase ItemDescription)(strcase "*8\" on 14\"*"))
                    (wcmatch(strcase ItemDescription)(strcase "*8 on 14*"))
                    (wcmatch(strcase ItemDescription)(strcase "*8\" on 16\"*"))
                    (wcmatch(strcase ItemDescription)(strcase "*8 on 16*"))
                    (wcmatch(strcase ItemDescription)(strcase "*8\" on 18\"*"))
                    (wcmatch(strcase ItemDescription)(strcase "*8 on 18*"))
                    (wcmatch(strcase ItemDescription)(strcase "*10\" on 12\"*"))
                    (wcmatch(strcase ItemDescription)(strcase "*10 on 12*"))
                    (wcmatch(strcase ItemDescription)(strcase "*10\" on 14\"*"))
                    (wcmatch(strcase ItemDescription)(strcase "*10 on 14*"))
                    (wcmatch(strcase ItemDescription)(strcase "*10\" on 16\"*"))
                    (wcmatch(strcase ItemDescription)(strcase "*10 on 16*"))
                    (wcmatch(strcase ItemDescription)(strcase "*10\" on 18\"*"))
                    (wcmatch(strcase ItemDescription)(strcase "*10 on 18*"))
                    (wcmatch(strcase ItemDescription)(strcase "*12\" on 14\"*"))
                    (wcmatch(strcase ItemDescription)(strcase "*12 on 14*"))
                    (wcmatch(strcase ItemDescription)(strcase "*12\" on 16\"*"))
                    (wcmatch(strcase ItemDescription)(strcase "*12 on 16*"))
                    (wcmatch(strcase ItemDescription)(strcase "*12\" on 18\"*"))
                    (wcmatch(strcase ItemDescription)(strcase "*12 on 18*"))
                    (wcmatch(strcase ItemDescription)(strcase "*12\" on 20\"*"))
                    (wcmatch(strcase ItemDescription)(strcase "*12 on 20*"))
                    (wcmatch(strcase ItemDescription)(strcase "*14\" on 16\"*"))
                    (wcmatch(strcase ItemDescription)(strcase "*14 on 16*"))
                    (wcmatch(strcase ItemDescription)(strcase "*14\" on 18\"*"))
                    (wcmatch(strcase ItemDescription)(strcase "*14 on 18*"))))
                 )
                 (and
                 (or(wcmatch(strcase ItemSourceFileName)(strcase "*Round Access Door*"))
                    (wcmatch(strcase ItemSourceFileName)(strcase "*#7 Access Door*")))
                 (not(or(wcmatch(strcase ItemDescription)(strcase "*6\"*"))
                    (wcmatch(strcase ItemDescription)(strcase "*8\"*"))
                    (wcmatch(strcase ItemDescription)(strcase "*10\"*"))
                    (wcmatch(strcase ItemDescription)(strcase "*12\"*"))
                    (wcmatch(strcase ItemDescription)(strcase "*14\"*"))))
                 )
                 (and
                 (or(wcmatch(strcase ItemSourceFileName)(strcase "*Conical Flat Tap*"))
                    (wcmatch(strcase ItemSourceFileName)(strcase "*Flat Conical 1\" Flg*"))
                    (wcmatch ItemCID "345"))
                 (not(or(wcmatch(strcase ItemDescription)(strcase "*5\"*"))
                    (wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(and(wcmatch ItemCID "51")(wcmatch(strcase ItemSourceFileName)(strcase "*6\" Start Collar wFlg*"))(wcmatch(strcase ItemDescription)(strcase "*for Damper*")))
                    (and(wcmatch ItemCID "51")(wcmatch(strcase ItemDescription)(strcase "*Damper*"))))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(and(wcmatch ItemCID "51")(wcmatch(strcase ItemSourceFileName)(strcase "*6\" Start Collar wFlg*"))(not(wcmatch(strcase ItemDescription)(strcase "*for Damper*"))))
                    (and(wcmatch ItemCID "51")(not(wcmatch(strcase ItemDescription)(strcase "*Damper*")))))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))))
                 )
                 (and
                 (or(wcmatch(strcase ItemSourceFileName)(strcase "Coupling")))
                 (not(or(wcmatch(strcase ItemDescription)(strcase "*6\"*"))
                    (wcmatch(strcase ItemDescription)(strcase "*7\"*"))
                    (wcmatch(strcase ItemDescription)(strcase "*8\"*"))
                    (wcmatch(strcase ItemDescription)(strcase "*9\"*"))
                    (wcmatch(strcase ItemDescription)(strcase "*10\"*"))
                    (wcmatch(strcase ItemDescription)(strcase "*12\"*"))
                    (wcmatch(strcase ItemDescription)(strcase "*14\"*"))
                    (wcmatch(strcase ItemDescription)(strcase "*16\"*"))
                    (wcmatch(strcase ItemDescription)(strcase "*18\"*"))))
                 )
                 (and
                 (or(wcmatch ItemCID "522")
                    (wcmatch(strcase ItemSourceFileName)(strcase "#2 Coupling")))
                 (not(or(= dim1 6)
                    (= dim1 7)
                    (= dim1 8)
                    (= dim1 9)
                    (= dim1 10)
                    (= dim1 12)
                    (= dim1 14)
                    (= dim1 16)
                    (= dim1 18)
                    (= dim1 20)))
                 )
                 )
                 )
                (setq Activity# "313")
                (if(and(not(or(wcmatch(strcase ItemService)(strcase "*Weld*"))(wcmatch(strcase ItemServiceType)(strcase "*Equipment*"))))
                   (or
                   (and(wcmatch(strcase ItemDescription)(strcase "Straight"))
                       (or(wcmatch(strcase c1Name)(strcase "TDF*"))
                          (wcmatch(strcase c2Name)(strcase "TDF*"))
                          (wcmatch(strcase c1Name)(strcase "*JF*"))
                          (wcmatch(strcase c2Name)(strcase "*JF*")))
                       (< ItemLengthAngle 56)
                   )
                   (and(wcmatch(strcase ItemDescription)(strcase "Straight"))
                       (or(wcmatch(strcase c1Name)(strcase "Stand S&D"))
                          (wcmatch(strcase c1Name)(strcase "Flat S&D"))
                          (wcmatch(strcase c2Name)(strcase "Stand S&D"))
                          (wcmatch(strcase c2Name)(strcase "Flat S&D"))
                          (wcmatch(strcase c1Name)(strcase "*S&D*"))
                          (wcmatch(strcase c2Name)(strcase "*S&D*")))
                       (< ItemLengthAngle 59))
                   (wcmatch(strcase ItemDescription)(strcase "Cut Joint"))
                   (wcmatch(strcase ItemDescription)(strcase "Plenum"))
                   (wcmatch(strcase ItemSourceFileName)(strcase "Transition"))
                   (wcmatch(strcase ItemSourceFileName)(strcase "*Rect Elbow"))
                   (wcmatch(strcase ItemSourceFileName)(strcase "F16"))
                   (wcmatch(strcase ItemSourceFileName)(strcase "F 16"))
                   (wcmatch(strcase ItemSourceFileName)(strcase "F17"))
                   (wcmatch(strcase ItemSourceFileName)(strcase "F41"))
                   (wcmatch(strcase ItemSourceFileName)(strcase "F2"))
                   (wcmatch(strcase ItemSourceFileName)(strcase "F4"))
                   (wcmatch(strcase ItemSourceFileName)(strcase "SQ-RD"))
                   (wcmatch(strcase ItemSourceFileName)(strcase "TDF CAP"))
                   (wcmatch(strcase ItemSourceFileName)(strcase "SD CAP"))
                   (wcmatch(strcase ItemSourceFileName)(strcase "PLUG CAP"))
                   (wcmatch(strcase ItemSourceFileName)(strcase "S&D CAP"))
                   ))
                  (setq Activity# "317")
                (if(wcmatch(strcase ItemService)(strcase "*Weld*"))
                  (setq Activity# "318")
                  (setq Activity# "Unassigned")
  ) ) ) ) ) ) ) ) ) ) );end ifs
      (vlax-put-property vla "CustomData" (strcat "ItemCID" " = " ItemCID ","))
      (vlax-put-property vla "CustomData" (strcat "Activity_#" " = " Activity# ","))
        (setq i (1+ i))
      );end while
  (UpdateJobData 10 jobName)
  (UpdateJobData 11 job#)
  (terpri)(princ "-- Activity Numbers and ItemCIDs Updated")(princ)
  (princ)
      );end progn
    (progn(terpri)(princ "-- Activity Number and ItemCID Update Skipped (Only Version 2019 or Later) --")(princ))
    );end if
  );end progn
  (terpri)(princ "Updating Layer Colors --")(princ)
  (c:Fix_Colors)
  (terpri)(princ "-- Layer Colors Updated")(princ)
  (if(not(= writeToVBCode nil))(progn(close writeToVBCode)(setq writeToVBCode nil)))
  (if(not(= vbcode nil))(progn(vl-file-delete vbCode)(setq vbcode nil)))
  (if(not(= doc nil))(vla-endundomark doc))
  (terpri)(princ "-- Update Complete")(princ)
  ;(command-s "._qsave" (if(> (getvar 'cmdactive) 0) "")(if(> (getvar 'cmdactive) 0) "N"))
  (princ)
(END_ROUTINE));end defun
