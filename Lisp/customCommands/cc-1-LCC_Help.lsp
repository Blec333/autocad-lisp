;|
APPLOAD DEPENDENCIES TO INCLUDE

  UTILITIES:
    utilityFunctions.lsp

  COMMANDS:
    
|;

(defun c:LCC_Help()
(OUTSIDE_LOOP_VARIABLES nil)(terpri)
(princ "The current drawing location is: ")(terpri)
(princ dwgDirectory)(terpri)
(princ "The current drawing name is: ")(terpri)
(princ dwgName)(terpri)
(princ "Your default excel launch path is: ")(terpri)
(princ excel)(terpri)
(princ "Your active seismic block reference location is: ")(terpri)
(princ SeismicBlock)(terpri)
(princ "Your active grille reference location is: ")(terpri)
(princ Grille)(terpri)
(princ " ")(terpri)
(princ "USER SETUP INFORMATION")(terpri)
(princ "In order to parse information correctly, the list setup file (CDDetail.MAP: provided with package) must be organized as such: ")(terpri)
(princ "ItemCID")(terpri)
(princ "C1 X coordinate")(terpri)
(princ "C1 Y coordinate")(terpri)
(princ "C1 Z coordinate")(terpri)
(princ "     - Repeat this pattern through connector # 25")(terpri)
(princ "Dimension number value 1")(terpri)
(princ "Dimension number value 2")(terpri)
(princ "Dimension number value 3")(terpri)
(princ "     - Repeat this pattern through dimension # 200")(terpri)
(princ (strcat "CDDetail.MAP should be copied to this location: " curFabPath))(terpri)
(princ " ")(terpri)
(princ "Command Help Format:------------------------------------------------------------------------------------")(terpri)
(princ "Tier - Shortcut - Command Name:                    Description")(terpri)
(princ " ")(terpri)
(princ "TIER 1 --------------------------------------------------------------------------------------------------------------")(terpri)
(princ "T1   - 2V       - Split_View_Into_2:               Spilt the current view with a vertical seperation into 2 views ")(terpri)
(princ "T1   - AA       - Attacher_On:                     Turns of the attacher arrow; Asks for selection")(terpri)
(princ "T1   - AD       - Adjust_Dampers:                  Choose from provided damper options to be applied to any number of items.")(terpri)
(princ "T1   - AF       - Attacher_Off:                    Turns off the attacher arrow")(terpri)
(princ "T1   - AG       - Add_Grille:                      Adds grille to connector and reduces dimensions by 2")(terpri)
(princ "T1   - CR       - Copy_Rotate:                     Choose basepoint, move the copy, rotate to desired angle")(terpri)
(princ "T1   - CX       - Copy_X_Axis:                     Pick points to define move; Axis is defined by the current UCS;")(terpri)
(princ "T1   - CY       - Copy_Y_Axis:                     Pick points to define move; Axis is defined by the current UCS;")(terpri)
(princ "T1   - CZ       - Copy_Z_Axis:                     Pick points to define move; Axis is defined by the current UCS;")(terpri)
(princ "T1   - DB       - Debug_Script:                    Execute the debug script file (predetermined location)")(terpri)
(princ "T1   - DSF      - Dimside_Off:                     Turns dimside off (Default position - does not factor in insulation for")(terpri)
(princ "                                                        dimension display)")(terpri)
(princ "T1   - DSO      - Dimside_On:                      Turns dimside on (Displays measurements with consideration for insulation)")(terpri)
(princ "T1   - DUMP     - Item_Information_Dump:           Dumps various information formats for selected item")(terpri)
(princ "T1   - EntS     - Select_Entity:                   Used within programs; Selects the current entity in a loop")(terpri)
(princ "T1   - ES       - Execute_Script:                  Opens default script location for selection & execution")(terpri)
(princ "T1   - FD       - Fix_Download:                    Fixes past issues; ie: unexplained changes on downloads")(terpri)
(princ "T1   - FF       - Flex_Fill:                       Flexfill command shortcut")(terpri)
(princ "T1   - FL       - Flip:                            Flips the object 180 degrees")(terpri)
(princ "T1   - FSD90    - Rotate_FSD_Motor:                Rotates only the motor orientation around the selected FSD")(terpri)
(princ "T1   - FV       - Front_View:                      Move camera perspective to front view")(terpri)
(princ "T1   - FXV      - Fix_Variables:                   Sets specific variables (various applications)")(terpri)
(princ "T1   - GEL      - Get_Entity_List:                 Displays CADmep properties associated with the selected item")(terpri)
(princ "T1   - GKAC     - Get_Keyboard_ASCII_Character:    Enter command and push a key; Get the ASCII character association")(terpri)
(princ "T1   - HC       - HangerCommand:                   At the moment, applied hangers honor the current service, not the duct service;")(terpri)
(princ "                                                        Do each service separately and be sure the active service is set to the")(terpri)
(princ "                                                        applicable service.")(terpri)
(princ "T1   - IU       - Item_Update:                     Updates selected items to current database standards")(terpri)
(princ "T1   - LAF      - List_All_Functions:              Lists available functions")(terpri)
(princ "T1   - LC       - Layer_Make_Current:              Make selected item's layer current")(terpri)
(princ "T1   - LF       - Layer_Off:                       Turn off selected item's layer")(terpri)
(princ "T1   - LI       - Layer_Isolate:                   Isolates layer of selected items")(terpri)
(princ "T1   - LI       - Layer_Isolate:                   Isolates layer of selected items")(terpri)
(princ "T1   - LM       - Layer_Match:                     Match source item's layer to destination item")(terpri)
(princ "T1   - LN       - Layers_On:                       Turn on all non-frozen layers")(terpri)
(princ "T1   - LU       - Layer_Unlock:                    Unlock selected item's layer")(terpri)
(princ "T1   - LV       - Last_View:                       Changes view to the previous view and previous UCS")(terpri)
(princ "T1   - LVW      - Last_View_WCS:                   Changes view to the previous view and world UCS")(terpri)
(princ "T1   - MP       - Move_Previous:                   Moves the previously active selection set")(terpri)
(princ "T1   - MR       - Move_Rotate:                     Move and rotate a single item")(terpri)
(princ "T1   - MRR      - Move_Rotate_Repeat:              Move and rotate multiple items")(terpri)
(princ "T1   - MT       - MultiText_Box:                   Inserts a Multi-text Box with a single click")(terpri)
(princ "T1   - MZ       - Move_Along_Z:                    Move only along the Z axis; positive or negative distance")(terpri)
(princ "T1   - NO       - Numbers_Off:                     Turns off all numbers")(terpri)
(princ "T1   - NO       - Numbers_On:                      Turn on numbers for appropriate items")(terpri)
(princ "T1   - OAF      - Open_Alias_File:                 Opens the alias file - acad.pgp")(terpri)
(princ "T1   - PO       - Paste_To_Original_Coordinates:   Pastes clipboard information to original coordinates")(terpri)
(princ "T1   - R3       - Rotate_3D:                       Rotate around a defined axis; Usually snap to a center point to rotate around")(terpri)
(princ "                                                        - dragging the line is like dragging a rope; the line is anchored")(terpri)
(princ "                                                        to the first selected point while you can imagine yourself at the")(terpri)
(princ "                                                        second selected point staring back at the object; with that in mind")(terpri)
(princ "                                                        know that positive angles count counterclockwise from point of view.")(terpri)
(princ "T1   - RA       - Rotate_Around_Attacher:          Rotate around the designated connector by a designated amount")(terpri)
(princ "T1   - RAC      - Rotate_Around_Center:            Rotate around the center point 180 degrees")(terpri)
(princ "T1   - RR       - Rotate_Reference:                Select rotational basepoint, select circumfrential basepoint, select target")(terpri)
(princ "                                                        basepoint")(terpri)
(princ "T1   - RT       - Rotate_Text:                     Rotates CADmep item text; single selection")(terpri)
(princ "T1   - RV       - Right_View:                      Move camera perspective to right view")(terpri)
(princ "T1   - SE       - Size_&_Elevation_Cycle:          Cycles through size & elevation text visibility options")(terpri)
(princ "T1   - SF       - Selection_Fix:                   Fixes those annoying moments where you can't select the object")(terpri)
(princ "T1   - SL       - Select_Last_Added:               Selects the most recent object addition to the drawing database")(terpri)
(princ "T1   - SP       - Select_Previous:                 Reselects the previously active selection set")(terpri)
(princ "T1   - T        - Make_Text_Layer_Current:         Makes the \"_Text\" layer current")(terpri)
(princ "T1   - TAF      - Text_Alias_Off                   Turns off alias text for selected items")(terpri)
(princ "T1   - TAO      - Text_Alias_On                    Turns on alias text for selected items")(terpri)
(princ "T1   - TC       - Text_Cloud:                      Apply a review cloud on the \"_Text\" layer")(terpri)
(princ "T1   - TD       - Toggle_Dimside:                  Toggles whether the dimensions are read and displayed based on the inside or")(terpri)
(princ "                                                        outside of the item with consideration for insulation")(terpri)
(princ "T1   - TEF      - Text_Elevation_Off               Turns off elevation text for selected items")(terpri)
(princ "T1   - TEO      - Text_Elevation_On                Turns on elevation text for selected items")(terpri)
(princ "T1   - TF       - Text_All_Off                     Turns off all text for selected items")(terpri)
(princ "T1   - TG       - Toggle_Grille:                   Use with HETO tap; Manipulates tap by adjusting sizes to shop standard minimums")(terpri)
(princ "                                                        and adding damper in preparation to add a grille (turns connector to 1 Flg In)")(terpri)
(princ "T1   - TLF      - Text_Length_Off                  Turns off length text for selected items")(terpri)
(princ "T1   - TLO      - Text_Length_On                   Turns on length text for selected items")(terpri)
(princ "T1   - TM       - Text_Move:                       Moves CADmep item text; single selection")(terpri)
(princ "T1   - TNF      - Text_Numbers_Off                 Turns off number text for all items")(terpri)
(princ "T1   - TNF      - Toggle_No-Fly_Zone:              Toggles an insulation entitled \"No-Fly Zone\" for clashing purposes")(terpri)
(princ "T1   - TNO      - Text_Numbers_On:                 Turns on number text for appropriate items")(terpri)
(princ "T1   - TO       - Text_All_On                      Turns on all text for selected items")(terpri)
(princ "T1   - TOF      - Text_Offset_Off                  Turns off offset text for selected items")(terpri)
(princ "T1   - TOO      - Text_Offset_On                   Turns on offset text for selected items")(terpri)
(princ "T1   - TSF      - Text_Size_Off                    Turns off size text for selected items")(terpri)
(princ "T1   - TSO      - Text_Size_On                     Turns on size text for selected items")(terpri)
(princ "T1   - TTA      - Text_Toggle_Alias                Toggles alias text for selected items")(terpri)
(princ "T1   - TTE      - Text_Toggle_Elevation            Toggles elevation text for selected items")(terpri)
(princ "T1   - TTL      - Text_Toggle_Length               Toggles length text for selected items")(terpri)
(princ "T1   - TTN      - Text_Toggle_Numbers              Toggles number text for selected items")(terpri)
(princ "T1   - TTO      - Text_Toggle_Offset               Toggles offset text for selected items")(terpri)
(princ "T1   - TTS      - Text_Toggle_Size                 Toggles size text for selected items")(terpri)
(princ "T1   - TV       - Top_View:                        Move camera perspective to top view")(terpri)
(princ "T1   - TZ       - Toggle_Z_Snaplock:               Toggles the Z-axis lock for snaps")(terpri)
(princ "T1   - WV       - World_View:                      Changes view to plan view and world UCS")(terpri)
(princ "T1   - XCD      - Delete_All_Xclips:               Delete Xref clipping planes")(terpri)
(princ "T1   - XRL      - Import_Xref_on_Custom_Layer:     Auto assign xref to its own layer and lock the layer")(terpri)
(princ "T1   - XX       - Move_X_Axis:                     Pick points to define move; Axis is defined by the current UCS;")(terpri)
(princ "T1   - YY       - Move_Y_Axis:                     Pick points to define move; Axis is defined by the current UCS;")(terpri)
(princ "T1   - ZZ       - Move_Z_Axis:                     Pick points to define move; Axis is defined by the current UCS;")(terpri)
(princ " ")(terpri)
(princ "TIER 2 --------------------------------------------------------------------------------------------------------------")(terpri)
(princ "T2   - 38ROD    - Switch_KS7L_to_38Rod_Damper:     Converts KS7L dampers to 3/8 Rod dampers; Ignores non KS7L dampers")(terpri)
(princ "T2   - C1       - C1:                              Cycles connection 1 around the most common connections (change multiple items at once)")(terpri)
(princ "T2   - C2       - C2:                              Cycles connection 2 around the most common connections (change multiple items at once)")(terpri)
(princ "T2   - CC       - Connection_Cycle:                If connections are at default or SMACNA standard, this cycles connection step downs")(terpri)
(princ "T2   - CF       - Connection_Fix:                  This corrects selected items to SMACNA standards for given size and pressure class")(terpri)
(princ "T2   - DE       - Dimension_at_Elevation:          Dimension on dimension layer at elevation")(terpri)
(princ "T2   - DC       - Damper_Cycle:                    Cycles dampers on/off")(terpri)
(princ "T2   - DW       - Create_DoubleWall_Patterns:      Creates doublewall inside patterns within selected items")(terpri)
(princ "T2   - HS       - Hanger_Stretch_to_Section:       Stretches all hangers to assigned section heights respectively")(terpri)
(princ "T2   - IC       - Insulation_Cycle:                Cycles insulation type")(terpri)
(princ "T2   - IG       - Insulation_Gauge_Cycle:          Cycles insulation thickness within type")(terpri)
(princ "T2   - IR       - Insulation_Reset:                Set or reset insulation across the selection; enter thickness per return/supply")(terpri)
(princ "T2   - ISC      - Insulation_Specification_Cycle:  Cycles insulation specification setting")(terpri)
(princ "T2   - ISR      - Item_Specification_Repair:       Repairs item specification to appropriate setting based on item services")(terpri)
(princ "T2   - KS7L     - Switch_38Rod_to_KS7L_Damper:     Converts 3/8 Rod dampers to KS7L  dampers; Ignores non 3/8 Rod dampers")(terpri)
(princ "T2   - MDE      - Multi_Dimension_Edit:            Edit any dimension for any amount of items; use index location")(terpri)
(princ "T2   - MOE      - Multi_Option_Edit:               Edit any option for any amount of items; use index location")(terpri)
(princ "T2   - SD       - Size_Down_Item:                  Increments item dimensions down by 2 if above 11 and by 1 otherwise; Increments")(terpri)
(princ "T2   - SDW      - Select_DoubleWall_Patterns:      Selects the doublewall inside patterns that have been created")(terpri)
(princ "T2   - SS       - Search_Specification:            Allows a search for items based on database specification then presents")(terpri)
(princ "T2   - SSS      - Select_Similar_SourceFileName:   Selects all items in drawing of the same source file name as the chosen item")(terpri)
(princ "T2   - SU       - Size_Up_Item:                    Increments item dimensions up by 2 if above 11 and by 1 otherwise; Increments")(terpri)
(princ "T2   - SV       - Improved_Section_View:           Section view but with usable grips and zooms to crossed object")(terpri)
(princ " ")(terpri)
(princ "TIER 3 --------------------------------------------------------------------------------------------------------------")(terpri)
(princ "T3   - AH       - Auto_Hatch_FSD:                  Automatically hatches FSDs (items based on \"Fire Damper\" service type)")(terpri)
(princ "T3   - AT       - Auto_Text:                       Intelligent auto texting makes desicions about text visibility and postion")(terpri)
(princ "T3   - C2D      - Create_2D:                Creates a scaled 2D drawing for gps coordinate layout")(terpri)
(princ "T3   - ILP      - Insert_ACAD_Layout_Points:       Applies traditional trimble points to seismic kickers")(terpri)
(princ "T3   - IPE      - Improved_Point_Export:           Captures coordinates in csv format")(terpri)
(princ "T3   - IRN      - Improved_ReNumber:               Automatically renumbers based on service and type")(terpri)
(princ "T3   - LLP      - Label_Layout_Points:             Places circles at any drawing's support point locations and labels them with size")(terpri)
(princ "T3   - LP       - Layout_Prep:                     This runs \"Improved_ReNumber\", \"Improved_Point_Export\" & \"Create_2D\" consecutively")(terpri)
(princ "T3   - UD       - Update_Drawing:                  This will update the template, blocks, certain layers, dimstyles, textstyles, services, specifications, activity numbers and ItemCIDs.")(terpri)

(textscr)
(princ)
);end defun
