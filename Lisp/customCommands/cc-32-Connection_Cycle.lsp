;|
APPLOAD DEPENDENCIES TO INCLUDE

  UTILITIES:
    utilityFunctions.lsp

  COMMANDS:
    
|;

(defun c:Connection_Cycle ()
;;;; CC = CALLS UP THE CONNECTION CYCLING FILE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if item.connector[1].value = \"TDF \" and item.connector[2].value = \"TDF \" then" writeToVBCode)
(write-line "REM ==== BEGIN JF STEP DOWN & TDF FUNCTION ====" writeToVBCode)
(write-line "dim c1Num = 1" writeToVBCode)
(write-line "dim c1Name = \"JF 1\"+qt+\" + qt + \" DD\"" writeToVBCode)
(write-line "dim c1Grp = \"Duct - Flg Connector\"" writeToVBCode)
(write-line "dim c2Num = 2" writeToVBCode)
(write-line "dim c2Name = \"TDF \"" writeToVBCode)
(write-line "dim c2Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(write-line "REM ==== END JF STEP DOWN & TDF FUNCTION ====" writeToVBCode)
(write-line "elseif item.connector[1].value = \"JF 1\"+qt+\" + qt + \" DD\" and item.connector[2].value = \"TDF \" then" writeToVBCode)
(write-line "REM ==== BEGIN JF STEP DOWN & TDF FUNCTION ====" writeToVBCode)
(write-line "dim c1Num = 1" writeToVBCode)
(write-line "dim c1Name = \"TDF \"" writeToVBCode)
(write-line "dim c1Grp = \"Duct - Flg Connector\"" writeToVBCode)
(write-line "dim c2Num = 2" writeToVBCode)
(write-line "dim c2Name = \"JF 1\"+qt+\" + qt + \" DD\"" writeToVBCode)
(write-line "dim c2Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "item.update()" writeToVBCode)
(write-line "REM ==== END JF STEP DOWN & TDF FUNCTION ====" writeToVBCode)
(write-line "elseif item.connector[1].value = \"TDF \" and item.connector[2].value = \"JF 1\"+qt+\" + qt + \" DD\" then" writeToVBCode)
(write-line "REM ==== BEGIN TDF FUNCTION ====" writeToVBCode)
(write-line "dim c1Num = 1" writeToVBCode)
(write-line "dim c1Name = \"TDF \"" writeToVBCode)
(write-line "dim c1Grp = \"Duct - Flg Connector\"" writeToVBCode)
(write-line "dim c2Num = 2" writeToVBCode)
(write-line "dim c2Name = \"TDF \"" writeToVBCode)
(write-line "dim c2Grp = \"Duct - Flg Connector\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END TDF FUNCTION ====" writeToVBCode)
(write-line "elseif item.connector[1].value = \"Flat S&D\" and item.connector[2].value = \"Flat S&D\" then" writeToVBCode)
(write-line "REM ==== BEGIN S&D STEP DOWN & FLAT S&D FUNCTION ====" writeToVBCode)
(write-line "dim c1Num = 1" writeToVBCode)
(write-line "dim c1Name = \"SD 1 SD\"" writeToVBCode)
(write-line "dim c1Grp = \"Duct - S&D\"" writeToVBCode)
(write-line "dim c2Num = 2" writeToVBCode)
(write-line "dim c2Name = \"Flat S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & FLAT S&D FUNCTION ====" writeToVBCode)
(write-line "elseif item.connector[1].value = \"SD 1 SD\" and item.connector[2].value = \"Flat S&D\" then" writeToVBCode)
(write-line "REM ==== BEGIN S&D STEP DOWN & FLAT S&D FUNCTION ====" writeToVBCode)
(write-line "dim c1Num = 1" writeToVBCode)
(write-line "dim c1Name = \"Flat S&D\"" writeToVBCode)
(write-line "dim c1Grp = \"Duct - S&D\"" writeToVBCode)
(write-line "dim c2Num = 2" writeToVBCode)
(write-line "dim c2Name = \"SD 1 SD\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & FLAT S&D FUNCTION ====" writeToVBCode)
(write-line "elseif item.connector[1].value = \"Flat S&D\" and item.connector[2].value = \"SD 1 SD\" then" writeToVBCode)
(write-line "REM ==== BEGIN S&D STEP DOWN & FLAT S&D FUNCTION ====" writeToVBCode)
(write-line "dim c1Num = 1" writeToVBCode)
(write-line "dim c1Name = \"Flat S&D\"" writeToVBCode)
(write-line "dim c1Grp = \"Duct - S&D\"" writeToVBCode)
(write-line "dim c2Num = 2" writeToVBCode)
(write-line "dim c2Name = \"Flat S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & FLAT S&D FUNCTION ====" writeToVBCode)
(write-line "elseif item.connector[1].value = \"Stand S&D\" and item.connector[2].value = \"Stand S&D\" then" writeToVBCode)
(write-line "REM ==== BEGIN S&D STEP DOWN & STAND S&D FUNCTION ====" writeToVBCode)
(write-line "dim c1Num = 1" writeToVBCode)
(write-line "dim c1Name = \"SD 1 SD\"" writeToVBCode)
(write-line "dim c1Grp = \"Duct - S&D\"" writeToVBCode)
(write-line "dim c2Num = 2" writeToVBCode)
(write-line "dim c2Name = \"Stand S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & STAND S&D FUNCTION ====" writeToVBCode)
(write-line "elseif item.connector[1].value = \"SD 1 SD\" and item.connector[2].value = \"Stand S&D\" then" writeToVBCode)
(write-line "REM ==== BEGIN S&D STEP DOWN & STAND S&D FUNCTION ====" writeToVBCode)
(write-line "dim c1Num = 1" writeToVBCode)
(write-line "dim c1Name = \"Stand S&D\"" writeToVBCode)
(write-line "dim c1Grp = \"Duct - S&D\"" writeToVBCode)
(write-line "dim c2Num = 2" writeToVBCode)
(write-line "dim c2Name = \"SD 1 SD\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & STAND S&D FUNCTION ====" writeToVBCode)
(write-line "elseif item.connector[1].value = \"Stand S&D\" and item.connector[2].value = \"SD 1 SD\" then" writeToVBCode)
(write-line "REM ==== BEGIN S&D STEP DOWN & STAND S&D FUNCTION ====" writeToVBCode)
(write-line "dim c1Num = 1" writeToVBCode)
(write-line "dim c1Name = \"Stand S&D\"" writeToVBCode)
(write-line "dim c1Grp = \"Duct - S&D\"" writeToVBCode)
(write-line "dim c2Num = 2" writeToVBCode)
(write-line "dim c2Name = \"Stand S&D\"" writeToVBCode)
(write-line "dim c2Grp = \"Duct - S&D\"" writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[c1Num].value = c1Name" writeToVBCode)
(write-line "item.connector[c1Num].locked = true" writeToVBCode)
(write-line "item.connector[c2Num].value = c2Name" writeToVBCode)
(write-line "item.connector[c2Num].locked = true" writeToVBCode)
(write-line "if item.connector[c1Num].group <> c1Grp then" writeToVBCode)
(write-line "connFind(c1Num,c1Grp,c1Name)" writeToVBCode)
(write-line "end if" writeToVBCode)
(write-line "if item.connector[c2Num].group <> c2Grp then" writeToVBCode)
(write-line "connFind(c2Num,c2Grp,c2Name)" writeToVBCode)
(write-line "end if" writeToVBCode)
(write-line "REM ==== END S&D STEP DOWN & STAND S&D FUNCTION ====" writeToVBCode)
(write-line "end if" writeToVBCode)
(write-line "i = i + 1" writeToVBCode)
(write-line "end while" writeToVBCode)
  (close writeToVBCode)
  (Executescript vbCode)
  (vl-file-delete vbCode)
  (prompt "Cycled to the next appropriate common connection option...")(princ)
  (princ)
(END_ROUTINE));end defun
