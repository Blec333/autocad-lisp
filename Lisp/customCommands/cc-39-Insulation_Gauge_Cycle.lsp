;|
APPLOAD DEPENDENCIES TO INCLUDE

  UTILITIES:
    utilityFunctions.lsp

  COMMANDS:
    
|;

(defun c:Insulation_Gauge_Cycle ()
;;;; IG = CYCLES INSULATION GAUGE WHERE APPROPRIATE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "if (wildcard(item.insulation.material,\"Duct Wrap\")=1) then" writeToVBCode)
(write-line "if (item.insulation.gauge = 1.5) then" writeToVBCode)
(write-line "item.insulation.gauge = 2" writeToVBCode)
(write-line "elseif (item.insulation.gauge = 2) then" writeToVBCode)
(write-line "item.insulation.gauge = 3" writeToVBCode)
(write-line "elseif (item.insulation.gauge = 3) then" writeToVBCode)
(write-line "item.insulation.gauge = 4" writeToVBCode)
(write-line "elseif (item.insulation.gauge = 4) then" writeToVBCode)
(write-line "item.insulation.gauge = 1" writeToVBCode)
(write-line "elseif (item.insulation.gauge = 1) then" writeToVBCode)
(write-line "item.insulation.gauge = 1.5" writeToVBCode)
(write-line "end if" writeToVBCode)
(write-line "elseif (wildcard(item.insulation.material,\"1-1/2 LB\")=1) and (item.doublewall = false) then" writeToVBCode)
(write-line "if (item.insulation.gauge = 1) then" writeToVBCode)
(write-line "item.insulation.gauge = 1.5" writeToVBCode)
(write-line "elseif (item.insulation.gauge = 1.5) then" writeToVBCode)
(write-line "item.insulation.gauge = 2" writeToVBCode)
(write-line "elseif (item.insulation.gauge = 2) then" writeToVBCode)
(write-line "item.insulation.gauge = 0.5" writeToVBCode)
(write-line "elseif (item.insulation.gauge = 0.5) then" writeToVBCode)
(write-line "item.insulation.gauge = 1" writeToVBCode)
(write-line "end if" writeToVBCode)
(write-line "elseif (wildcard(item.insulation.material,\"Fire Barrier Duct Wrap\")=1) then" writeToVBCode)
(write-line "if (item.insulation.gauge = 2) then" writeToVBCode)
(write-line "item.insulation.gauge = 3" writeToVBCode)
(write-line "elseif (item.insulation.gauge = 3) then" writeToVBCode)
(write-line "item.insulation.gauge = 4" writeToVBCode)
(write-line "elseif (item.insulation.gauge = 4) then" writeToVBCode)
(write-line "item.insulation.gauge = 5" writeToVBCode)
(write-line "elseif (item.insulation.gauge = 5) then" writeToVBCode)
(write-line "item.insulation.gauge = 6" writeToVBCode)
(write-line "elseif (item.insulation.gauge = 6) then" writeToVBCode)
(write-line "item.insulation.gauge = 7" writeToVBCode)
(write-line "elseif (item.insulation.gauge = 7) then" writeToVBCode)
(write-line "item.insulation.gauge = 8" writeToVBCode)
(write-line "elseif (item.insulation.gauge = 8) then" writeToVBCode)
(write-line "item.insulation.gauge = 9" writeToVBCode)
(write-line "elseif (item.insulation.gauge = 9) then" writeToVBCode)
(write-line "item.insulation.gauge = 10" writeToVBCode)
(write-line "elseif (item.insulation.gauge = 10) then" writeToVBCode)
(write-line "item.insulation.gauge = 2" writeToVBCode)
(write-line "end if" writeToVBCode)
(write-line "elseif item.doublewall = true then" writeToVBCode)
(write-line "if (item.insulation.gauge = 1) then" writeToVBCode)
(write-line "item.insulation.gauge = 1.5" writeToVBCode)
(write-line "elseif (item.insulation.gauge = 1.5) then" writeToVBCode)
(write-line "item.insulation.gauge = 2" writeToVBCode)
(write-line "elseif (item.insulation.gauge = 2) then" writeToVBCode)
(write-line "item.insulation.gauge = 0.5" writeToVBCode)
(write-line "elseif (item.insulation.gauge = 0.5) then" writeToVBCode)
(write-line "item.insulation.gauge = 1" writeToVBCode)
(write-line "end if" writeToVBCode)
(write-line "item.update()" writeToVBCode)
(write-line "end if" writeToVBCode)
(write-line "item.update()" writeToVBCode)
(write-line "i = i + 1" writeToVBCode)
(write-line "end while" writeToVBCode)
  (close writeToVBCode)
  (Executescript vbCode)
  (vl-file-delete vbCode)
  (prompt "Cycled insulation gauge")(princ)
  (princ)
(END_ROUTINE));end defun
