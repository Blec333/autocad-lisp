;|
APPLOAD DEPENDENCIES TO INCLUDE

  UTILITIES:
    utilityFunctions.lsp

  COMMANDS:
    
|;

(defun c:C2 ()
  (setq i 0
        sset (ssget '((0 . "MAPS_SOLID"))));end setq
  (OUTSIDE_LOOP_VARIABLES sset)
  (while(< i limit)
    (INSIDE_LOOP_VARIABLES sset i)
    (setq cNumber "2"
          connectionName c2Name)
    (if(= c2Spec "TDF")
      (if(wcmatch connectionName "TDF*")
        (setq newConnection "JF")
        (if(wcmatch connectionName "JF")
          (setq newConnection "JF-OFF")
          (if(wcmatch connectionName "JF-OFF")
            (setq newConnection "Cap")
            (if(wcmatch connectionName "Cap")
              (setq newConnection "RAW")
              (if(wcmatch connectionName "RAW")
                (setq newConnection "PG")
                (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                          (setq newConnection "1.5 flg out")
                          (if(wcmatch connectionName "1.5 flg out")
                            (setq newConnection "1.5 flg in")
                            (if(wcmatch connectionName "1.5 flg in")
                              (setq newConnection "JF 1\" + qt + \" DD")
                              (if(wcmatch connectionName "JF 1\" DD")
                                (setq newConnection "JF 1.5\" + qt + \" DD")
                                (if(wcmatch connectionName "JF 1.5\" DD")
                                  (setq newConnection "JF 2\" + qt + \" DD")
                                  (if(wcmatch connectionName "JF 2\" DD")
                                    (setq newConnection "JF 3\" + qt + \" DD")
                                    (if(wcmatch connectionName "JF 3\" DD")
                                      (setq newConnection "JF 4\" + qt + \" DD")
                                      (if(wcmatch connectionName "JF 4\" DD")
                                        (setq newConnection "TDF ")
      ) ) ) ) ) ) ) ) ) ) ) ) ) ) ) ) )
    (if(= c2Spec "Stand S&D")
      (if(wcmatch connectionName "Stand S&D")
        (setq newConnection "4S")
        (if(wcmatch connectionName "4S")
          (setq newConnection "Cap")
          (if(wcmatch connectionName "Cap")
            (setq newConnection "RAW")
            (if(wcmatch connectionName "RAW")
              (setq newConnection "PG")
              (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                        (setq newConnection "1.5 flg out")
                        (if(wcmatch connectionName "1.5 flg out")
                          (setq newConnection "1.5 flg in")
                          (if(wcmatch connectionName "1.5 flg in")
                            (setq newConnection "SD 1 SD")
                            (if(wcmatch connectionName "SD 1 SD")
                              (setq newConnection "SD 1.5 SD")
                              (if(wcmatch connectionName "SD 1.5 SD")
                                (setq newConnection "SD 2 SD")
                                (if(wcmatch connectionName "SD 2 SD")
                                  (setq newConnection "Stand S&D")
      ) ) ) ) ) ) ) ) ) ) ) ) ) )
    (if(= c2Spec "Flat S&D")
      (if(wcmatch connectionName "Flat S&D")
        (setq newConnection "4S")
        (if(wcmatch connectionName "4S")
          (setq newConnection "Cap")
          (if(wcmatch connectionName "Cap")
            (setq newConnection "RAW")
            (if(wcmatch connectionName "RAW")
              (setq newConnection "PG")
              (if(wcmatch connectionName "PG")
                (setq newConnection "1 Flg In")
                (if(or(wcmatch connectionName "1 Flg In")(wcmatch connectionName "Tap Inside"))
                  (setq newConnection "1 Flg Out")
                  (if(wcmatch connectionName "1 Flg Out")
                    (setq newConnection "1.25 flg out")
                    (if(wcmatch connectionName "1.25 flg out")
                      (setq newConnection "1.25 flg in")
                      (if(wcmatch connectionName "1.25 flg in")
                        (setq newConnection "1.5 flg out")
                        (if(wcmatch connectionName "1.5 flg out")
                          (setq newConnection "1.5 flg in")
                          (if(wcmatch connectionName "1.5 flg in")
                            (setq newConnection "SD 1 SD")
                            (if(wcmatch connectionName "SD 1 SD")
                              (setq newConnection "SD 1.5 SD")
                              (if(wcmatch connectionName "SD 1.5 SD")
                                (setq newConnection "SD 2 SD")
                                (if(wcmatch connectionName "SD 2 SD")
                                  (setq newConnection "Flat S&D")
      ) ) ) ) ) ) ) ) ) ) ) ) ) )
      ) ) )
      (if(or(wcmatch connectionName "TDF*")
            (wcmatch connectionName "JF")
            (wcmatch connectionName "JF-OFF")
            (wcmatch connectionName "JF 1\" DD")
            (wcmatch connectionName "JF 1.5\" DD")
            (wcmatch connectionName "JF 2\" DD")
            (wcmatch connectionName "JF 3\" DD")
            (wcmatch connectionName "JF 4\" DD"))
        (setq connectionGroup "Duct - Flg Connector")
        (if(or(wcmatch connectionName "Cap")
              (wcmatch connectionName "RAW")
              (wcmatch connectionName "PG"))
          (setq connectionGroup "Duct - Other")
          (if(or(wcmatch connectionName "1 Flg Out")
                (wcmatch connectionName "1 Flg In")
                (wcmatch connectionName "1.25 flg out")
                (wcmatch connectionName "1.25 flg in")
                (wcmatch connectionName "1.5 flg out")
                (wcmatch connectionName "1.5 flg in"))
            (setq connectionGroup "Duct - Flanged")
            (if(wcmatch connectionName "Tap Inside")
            (setq connectionGroup "Duct - Flanged")
            (if(or(wcmatch connectionName "Flat S&D")
                  (wcmatch connectionName "4S")
                  (wcmatch connectionName "Stand S&D")
                  (wcmatch connectionName "SD 1 SD")
                  (wcmatch connectionName "SD 1.5 SD")
                  (wcmatch connectionName "SD 2 SD"))
              (setq connectionGroup "Duct - S&D")
      ) ) ) ) )
(write-line "dim qt = ASCII(34)" writeToVBCode)
(write-line (strcat "dim conNum = " cNumber) writeToVBCode)
(write-line (strcat "dim conName = \"" newConnection "\"") writeToVBCode)
(write-line (strcat "dim conGrp = \"" connectionGroup "\"") writeToVBCode)
(write-line "function connFind(cnum,cgrp,cnam)" writeToVBCode)
(write-line "dim count = 1" writeToVBCode)
(write-line "while item.connector[cnum].group <> cgrp" writeToVBCode)
(write-line "item.connector[cnum].value = count" writeToVBCode)
(write-line "count = count + 1" writeToVBCode)
(write-line "end while" writeToVBCode)
(write-line "while item.connector[cnum].value <> cnam" writeToVBCode)
(write-line "item.connector[cnum].value = count" writeToVBCode)
(write-line "count = count + 1" writeToVBCode)
(write-line "end while" writeToVBCode)
(write-line "end function" writeToVBCode)
(write-line "item.connector[conNum].value = conName" writeToVBCode)
(write-line "item.connector[conNum].locked = true" writeToVBCode)
(write-line "if item.connector[conNum].group <> conGrp then" writeToVBCode)
(write-line "connFind(conNum,conGrp,conName)" writeToVBCode)
(write-line "end if" writeToVBCode)
(if(and(= connectionGroup "Duct - Flg Connector")(= ItemCID "2"))
  (progn
    (write-line "if item.dim[7].value < 1.5 then" writeToVBCode)
    (write-line "item.dim[7].value = 1.5" writeToVBCode)
    (write-line "item.update()" writeToVBCode)
    (write-line "end if" writeToVBCode)
  );progn
);end if
(write-line "item.update()" writeToVBCode)
    (close writeToVBCode)
    (executescript vbCode sset)
    (setq writeToVBCode (open vbCode "w"))
    (princ (strcat "Connection " cNumber " changed from " connectionName " to " newConnection))(terpri)
    (setq i (1+ i))
  );end while
  (command "pselect" sset "")
  (command "regen")
  (princ)
(END_ROUTINE));end defun
