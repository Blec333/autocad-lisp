;|
APPLOAD DEPENDENCIES TO INCLUDE

  UTILITIES:
    utilityFunctions.lsp

  COMMANDS:
    
|;

(defun c:Damper_Cycle ()
;;;; DC = CYCLES DAMPER OPTIONS WHERE APPROPRIATE
(OUTSIDE_LOOP_VARIABLES nil)
(write-line "requires task.selection" writeToVBCode)
(write-line "dim i = 1" writeToVBCode)
(write-line "dim qt = ASCII(34)" writeToVBCode)
(write-line "while i <= task.selection.count" writeToVBCode)
(write-line "dim item = task.selection[i]" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnTapSqRdDamper ()" writeToVBCode)
(write-line "dim item = task.selection[i]" writeToVBCode)
(write-line "if (((item.CID = 345 or item.CID = 751 or item.CID = 51 or item.CID = 875) and item.dim[2].value <= 12) or (item.CID = 16 and item.dim[1].value <= 12) or (item.CID = 8 and item.dim[3].value <= 12)) then" writeToVBCode)
(write-line "if item.dampers = 1 then" writeToVBCode)
(write-line "if item.CID = 345 and item.damper[1].value = \"NONE\" then" writeToVBCode)
(write-line "if item.dim[9].locked = false then" writeToVBCode)
(write-line "item.dim[9].value = 6" writeToVBCode)
(write-line "end if" writeToVBCode)
(write-line "item.damper[1].value = \"KS7L-l\"" writeToVBCode)
(write-line "item.damper[1].locked = true" writeToVBCode)
(write-line "item.update()" writeToVBCode)
(write-line "elseif item.CID = 16 and item.damper[1].value = \"NONE\" then" writeToVBCode)
(write-line "if item.dim[2].locked = false then" writeToVBCode)
(write-line "item.dim[2].value = 6" writeToVBCode)
(write-line "end if" writeToVBCode)
(write-line "item.damper[1].value = \"KS7L-l\"" writeToVBCode)
(write-line "item.damper[1].locked = true" writeToVBCode)
(write-line "item.update()" writeToVBCode)
(write-line "elseif item.CID = 8 and item.damper[1].value = \"NONE\" then" writeToVBCode)
(write-line "if item.dim[8].locked = false then" writeToVBCode)
(write-line "item.dim[8].value = 6" writeToVBCode)
(write-line "end if" writeToVBCode)
(write-line "item.damper[1].value = \"KS7L-l\"" writeToVBCode)
(write-line "item.damper[1].locked = true" writeToVBCode)
(write-line "item.update()" writeToVBCode)
(write-line "end if" writeToVBCode)
(write-line "elseif item.dampers = 2 then" writeToVBCode)
(write-line "if item.CID = 51 and item.damper[2].value = \"NONE\" then" writeToVBCode)
(write-line "if item.dim[2].value >= 4 and item.dim[2].value <= 6 then" writeToVBCode)
(write-line "if item.dim[3].locked = false then" writeToVBCode)
(write-line "item.dim[3].value = 6" writeToVBCode)
(write-line "item.update()" writeToVBCode)
(write-line "end if" writeToVBCode)
(write-line "elseif item.dim[2].value >= 7 and item.dim[2].value <= 10 then" writeToVBCode)
(write-line "if item.dim[3].locked = false then" writeToVBCode)
(write-line "item.dim[3].value = 10" writeToVBCode)
(write-line "item.update()" writeToVBCode)
(write-line "end if" writeToVBCode)
(write-line "elseif item.dim[2].value >= 11 and item.dim[2].value <= 12 then" writeToVBCode)
(write-line "if item.dim[3].locked = false then" writeToVBCode)
(write-line "item.dim[3].value = 12" writeToVBCode)
(write-line "item.update()" writeToVBCode)
(write-line "end if" writeToVBCode)
(write-line "end if" writeToVBCode)
(write-line "item.damper[2].value = \"KS7L-l\"" writeToVBCode)
(write-line "item.damper[2].locked = true" writeToVBCode)
(write-line "item.update()" writeToVBCode)
(write-line "end if" writeToVBCode)
(write-line "elseif item.dampers = 3 then" writeToVBCode)
(write-line "if item.CID = 875 and item.damper[3].value = \"NONE\" then" writeToVBCode)
(write-line "if item.description = \"*saddle*\" then" writeToVBCode)
(write-line "if item.dim[3].locked = false then" writeToVBCode)
(write-line "item.dim[3].value = 6" writeToVBCode)
(write-line "end if" writeToVBCode)
(write-line "elseif item.description <> \"*saddle*\" then" writeToVBCode)
(write-line "if item.dim[3].locked = false then" writeToVBCode)
(write-line "item.dim[3].value = 15" writeToVBCode)
(write-line "end if" writeToVBCode)
(write-line "end if" writeToVBCode)
(write-line "item.damper[3].value = \"KS7L-l\"" writeToVBCode)
(write-line "item.damper[3].locked = true" writeToVBCode)
(write-line "item.update()" writeToVBCode)
(write-line "elseif item.CID = 751 and item.damper[3].value = \"NONE\" then" writeToVBCode)
(write-line "if item.dim[5].locked = false then" writeToVBCode)
(write-line "item.dim[5].value = 6" writeToVBCode)
(write-line "end if" writeToVBCode)
(write-line "item.damper[3].value = \"KS7L-l\"" writeToVBCode)
(write-line "item.damper[3].locked = true" writeToVBCode)
(write-line "item.update()" writeToVBCode)
(write-line "end if" writeToVBCode)
(write-line "item.update()" writeToVBCode)
(write-line "end if" writeToVBCode)
(write-line "elseif (((item.CID = 345 or item.CID = 751 or item.CID = 51 or item.CID = 875) and item.dim[2].value > 12) or (item.CID = 16 and item.dim[1].value > 12) or (item.CID = 8 and item.dim[3].value > 12)) then" writeToVBCode)
(write-line "if item.dampers = 1 then" writeToVBCode)
(write-line "if item.CID = 345 and item.damper[1].value = \"NONE\" then" writeToVBCode)
(write-line "if item.dim[9].locked = false then" writeToVBCode)
(write-line "item.dim[9].value = 6" writeToVBCode)
(write-line "end if" writeToVBCode)
(write-line "item.damper[1].value = \"3/8\"+qt+\" ROD-L\"" writeToVBCode)
(write-line "item.damper[1].locked = true" writeToVBCode)
(write-line "elseif item.CID = 16 and item.damper[1].value = \"NONE\" then" writeToVBCode)
(write-line "if item.dim[2].locked = false then" writeToVBCode)
(write-line "item.dim[2].value = 6" writeToVBCode)
(write-line "end if" writeToVBCode)
(write-line "item.damper[1].value = \"3/8\"+qt+\" ROD-L\"" writeToVBCode)
(write-line "item.damper[1].locked = true" writeToVBCode)
(write-line "item.update()" writeToVBCode)
(write-line "elseif item.CID = 8 and item.damper[1].value = \"NONE\" then" writeToVBCode)
(write-line "if item.dim[8].locked = false then" writeToVBCode)
(write-line "item.dim[8].value = 6" writeToVBCode)
(write-line "end if" writeToVBCode)
(write-line "item.damper[1].value = \"3/8\"+qt+\" ROD-L\"" writeToVBCode)
(write-line "item.damper[1].locked = true" writeToVBCode)
(write-line "item.update()" writeToVBCode)
(write-line "end if" writeToVBCode)
(write-line "elseif item.dampers = 2 then" writeToVBCode)
(write-line "if item.CID = 51 and item.damper[2].value = \"NONE\" then" writeToVBCode)
(write-line "if item.dim[2].value > 12 and item.dim[2].value <= 14 then" writeToVBCode)
(write-line "if item.dim[3].locked = false then" writeToVBCode)
(write-line "item.dim[3].value = 12" writeToVBCode)
(write-line "item.update()" writeToVBCode)
(write-line "end if" writeToVBCode)
(write-line "elseif item.dim[2].value >= 16 and item.dim[2].value <= 18 then" writeToVBCode)
(write-line "if item.dim[3].locked = false then" writeToVBCode)
(write-line "item.dim[3].value = 15" writeToVBCode)
(write-line "item.update()" writeToVBCode)
(write-line "end if" writeToVBCode)
(write-line "elseif item.dim[2].value >= 20 then" writeToVBCode)
(write-line "if item.dim[3].locked = false then" writeToVBCode)
(write-line "item.dim[3].value = 20" writeToVBCode)
(write-line "item.update()" writeToVBCode)
(write-line "end if" writeToVBCode)
(write-line "end if" writeToVBCode)
(write-line "item.damper[2].value = \"3/8\"+qt+\" ROD-L\"" writeToVBCode)
(write-line "item.damper[2].locked = true" writeToVBCode)
(write-line "end if" writeToVBCode)
(write-line "elseif item.dampers = 3 then" writeToVBCode)
(write-line "if item.CID = 875 and item.damper[3].value = \"NONE\" then" writeToVBCode)
(write-line "if item.description = \"*saddle*\" then" writeToVBCode)
(write-line "if item.dim[3].locked = false then" writeToVBCode)
(write-line "item.dim[3].value = 6" writeToVBCode)
(write-line "end if" writeToVBCode)
(write-line "elseif item.description <> \"*saddle*\" then" writeToVBCode)
(write-line "if item.dim[3].locked = false then" writeToVBCode)
(write-line "item.dim[3].value = 15" writeToVBCode)
(write-line "end if" writeToVBCode)
(write-line "end if" writeToVBCode)
(write-line "item.damper[3].value = \"3/8\"+qt+\" ROD-L\"" writeToVBCode)
(write-line "item.damper[3].locked = true" writeToVBCode)
(write-line "item.update()" writeToVBCode)
(write-line "elseif item.CID = 751 and item.damper[3].value = \"NONE\" then" writeToVBCode)
(write-line "if item.dim[9].locked = false then" writeToVBCode)
(write-line "item.dim[5].value = 6" writeToVBCode)
(write-line "end if" writeToVBCode)
(write-line "item.damper[3].value = \"3/8\"+qt+\" ROD-L\"" writeToVBCode)
(write-line "item.damper[3].locked = true" writeToVBCode)
(write-line "item.update()" writeToVBCode)
(write-line "end if" writeToVBCode)
(write-line "item.update()" writeToVBCode)
(write-line "end if" writeToVBCode)
(write-line "item.update()" writeToVBCode)
(write-line "end if" writeToVBCode)
(write-line "end function" writeToVBCode)
(write-line "function turnOffTapSqRdDamper ()" writeToVBCode)
(write-line "dim item = task.selection[i]" writeToVBCode)
(write-line "if item.dampers = 1 then" writeToVBCode)
(write-line "if item.CID = 345 and item.damper[1].value <> \"NONE\" then" writeToVBCode)
(write-line "if item.dim[9].locked = false then" writeToVBCode)
(write-line "item.dim[9].value = 0" writeToVBCode)
(write-line "end if" writeToVBCode)
(write-line "item.damper[1].value = \"NONE\"" writeToVBCode)
(write-line "item.damper[1].locked = true" writeToVBCode)
(write-line "item.update()" writeToVBCode)
(write-line "elseif item.CID = 16 and item.damper[1].value <> \"NONE\" then" writeToVBCode)
(write-line "if item.dim[2].locked = false then" writeToVBCode)
(write-line "item.dim[2].value = 6" writeToVBCode)
(write-line "end if" writeToVBCode)
(write-line "item.damper[1].value = \"NONE\"" writeToVBCode)
(write-line "item.damper[1].locked = true" writeToVBCode)
(write-line "item.update()" writeToVBCode)
(write-line "elseif item.CID = 8 and item.damper[1].value <> \"NONE\" then" writeToVBCode)
(write-line "if item.dim[8].locked = false then" writeToVBCode)
(write-line "item.dim[8].value = 3" writeToVBCode)
(write-line "end if" writeToVBCode)
(write-line "item.damper[1].value = \"NONE\"" writeToVBCode)
(write-line "item.damper[1].locked = true" writeToVBCode)
(write-line "item.update()" writeToVBCode)
(write-line "end if" writeToVBCode)
(write-line "elseif item.dampers = 2 then" writeToVBCode)
(write-line "if item.CID = 51 and item.damper[2].value <> \"NONE\" then" writeToVBCode)
(write-line "if item.dim[3].locked = false then" writeToVBCode)
(write-line "item.dim[3].value = 3.75" writeToVBCode)
(write-line "end if" writeToVBCode)
(write-line "item.damper[2].value = \"NONE\"" writeToVBCode)
(write-line "item.damper[2].locked = true" writeToVBCode)
(write-line "item.update()" writeToVBCode)
(write-line "end if" writeToVBCode)
(write-line "elseif item.dampers = 3 then" writeToVBCode)
(write-line "if item.CID = 875 and item.damper[3].value <> \"NONE\" then" writeToVBCode)
(write-line "if item.dim[3].locked = false then" writeToVBCode)
(write-line "item.dim[3].value = 6" writeToVBCode)
(write-line "end if" writeToVBCode)
(write-line "item.damper[3].value = \"NONE\"" writeToVBCode)
(write-line "item.damper[3].locked = true" writeToVBCode)
(write-line "item.update()" writeToVBCode)
(write-line "elseif item.CID = 751 and item.damper[3].value <> \"NONE\" then" writeToVBCode)
(write-line "if item.dim[5].locked = false then" writeToVBCode)
(write-line "item.dim[5].value = 0" writeToVBCode)
(write-line "end if" writeToVBCode)
(write-line "item.damper[3].value = \"NONE\"" writeToVBCode)
(write-line "item.damper[3].locked = true" writeToVBCode)
(write-line "item.update()" writeToVBCode)
(write-line "end if" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD2 ()" writeToVBCode)
(write-line "dim item = task.selection[i]" writeToVBCode)
(write-line "if (((item.CID = 53 or item.CID = 54 or item.CID = 345 or item.CID = 751 or item.CID = 51 or item.CID = 875) and item.dim[2].value <= 12) or ((item.CID = 807 or item.CID = 812 or item.CID = 16) and item.dim[1].value <= 12) or (item.CID = 8 and item.dim[3].value <= 12)) then" writeToVBCode)
(write-line "if item.CID = 53 or item.CID = 54 then" writeToVBCode)
(write-line "item.dim[5].value = 6" writeToVBCode)
(write-line "item.update()" writeToVBCode)
(write-line "elseif item.CID = 807 or item.CID = 812 then" writeToVBCode)
(write-line "item.dim[4].value = 6" writeToVBCode)
(write-line "item.update()" writeToVBCode)
(write-line "end if" writeToVBCode)
(write-line "item.damper[2].value = \"KS7L-l\"" writeToVBCode)
(write-line "item.damper[2].locked = true" writeToVBCode)
(write-line "item.update()" writeToVBCode)
(write-line "elseif (((item.CID = 53 or item.CID = 54) and item.dim[2].value > 12) or ((item.CID = 807 or item.CID = 812) and item.dim[1].value > 12) or (item.CID = 8 and item.dim[3].value > 12)) then" writeToVBCode)
(write-line "if item.CID = 53 or item.CID = 54 then" writeToVBCode)
(write-line "item.dim[5].value = 6" writeToVBCode)
(write-line "item.update()" writeToVBCode)
(write-line "elseif item.CID = 807 or item.CID = 812 then" writeToVBCode)
(write-line "item.dim[4].value = 6" writeToVBCode)
(write-line "item.update()" writeToVBCode)
(write-line "end if" writeToVBCode)
(write-line "item.damper[2].value = \"3/8\"+qt+\" ROD-L\"" writeToVBCode)
(write-line "item.damper[2].locked = true" writeToVBCode)
(write-line "item.update()" writeToVBCode)
(write-line "end if" writeToVBCode)
(write-line "end function" writeToVBCode)
(write-line "function turnOffD2 ()" writeToVBCode)
(write-line "dim item = task.selection[i]" writeToVBCode)
(write-line "if item.CID = 53 or item.CID = 54 then" writeToVBCode)
(write-line "item.dim[5].value = 0" writeToVBCode)
(write-line "item.damper[2].value = \"NONE\"" writeToVBCode)
(write-line "item.damper[2].locked = true" writeToVBCode)
(write-line "item.update()" writeToVBCode)
(write-line "elseif item.CID = 807 or item.CID = 812 then" writeToVBCode)
(write-line "item.dim[4].value = 1" writeToVBCode)
(write-line "item.damper[2].value = \"NONE\"" writeToVBCode)
(write-line "item.damper[2].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD3 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.damper[3].value = \"KS7L-l\"" writeToVBCode)
(write-line "item.damper[3].locked = true" writeToVBCode)
(write-line "item.update()" writeToVBCode)
(write-line "elseif item.CID = 807 or item.CID = 812 then" writeToVBCode)
(write-line "item.damper[3].value = \"KS7L-l\"" writeToVBCode)
(write-line "item.damper[3].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.damper[3].value = \"3/8\"+qt+\" ROD-L\"" writeToVBCode)
(write-line "item.damper[3].locked = true" writeToVBCode)
(write-line "item.update()" writeToVBCode)
(write-line "elseif item.CID = 807 or item.CID = 812 then" writeToVBCode)
(write-line "item.damper[3].value = \"3/8\"+qt+\" ROD-L\"" writeToVBCode)
(write-line "item.damper[3].locked = true" writeToVBCode)
(write-line "item.update()" writeToVBCode)
(write-line "end if" writeToVBCode)
(write-line "item.update()" writeToVBCode)
(write-line "end if" writeToVBCode)
(write-line "end function" writeToVBCode)
(write-line "function turnOffD3 ()" writeToVBCode)
(write-line "dim item = task.selection[i]" writeToVBCode)
(write-line "if item.CID = 53 or item.CID = 54 or item.CID = 807 or item.CID = 812 then" writeToVBCode)
(write-line "item.damper[3].value = \"NONE\"" writeToVBCode)
(write-line "item.damper[3].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD4 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.damper[4].value = \"KS7L-l\"" writeToVBCode)
(write-line "item.damper[4].locked = true" writeToVBCode)
(write-line "item.update()" writeToVBCode)
(write-line "elseif item.CID = 807 or item.CID = 812 then" writeToVBCode)
(write-line "item.damper[4].value = \"KS7L-l\"" writeToVBCode)
(write-line "item.damper[4].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.damper[4].value = \"3/8\"+qt+\" ROD-L\"" writeToVBCode)
(write-line "item.damper[4].locked = true" writeToVBCode)
(write-line "item.update()" writeToVBCode)
(write-line "elseif item.CID = 807 or item.CID = 812 then" writeToVBCode)
(write-line "item.damper[4].value = \"3/8\"+qt+\" ROD-L\"" writeToVBCode)
(write-line "item.damper[4].locked = true" writeToVBCode)
(write-line "item.update()" writeToVBCode)
(write-line "end if" writeToVBCode)
(write-line "item.update()" writeToVBCode)
(write-line "end if" writeToVBCode)
(write-line "end function" writeToVBCode)
(write-line "function turnOffD4 ()" writeToVBCode)
(write-line "dim item = task.selection[i]" writeToVBCode)
(write-line "if item.CID = 53 or item.CID = 54 or item.CID = 807 or item.CID = 812 then" writeToVBCode)
(write-line "item.damper[4].value = \"NONE\"" writeToVBCode)
(write-line "item.damper[4].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD2D3 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.dim[5].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.update()" writeToVBCode)
(write-line "elseif item.CID = 807 or item.CID = 812 then" writeToVBCode)
(write-line "item.dim[4].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.dim[5].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.update()" writeToVBCode)
(write-line "elseif item.CID = 807 or item.CID = 812 then" writeToVBCode)
(write-line "item.dim[4].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.update()" writeToVBCode)
(write-line "end if" writeToVBCode)
(write-line "item.update()" writeToVBCode)
(write-line "end if" writeToVBCode)
(write-line "end function" writeToVBCode)
(write-line "function turnOffD2D3 ()" writeToVBCode)
(write-line "dim item = task.selection[i]" writeToVBCode)
(write-line "if item.CID = 53 or item.CID = 54 then" writeToVBCode)
(write-line "item.dim[5].value = 0" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.update()" writeToVBCode)
(write-line "elseif item.CID = 807 or item.CID = 812 then" writeToVBCode)
(write-line "item.dim[4].value = 1" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "function turnOnD2D3D4 ()" writeToVBCode)
(write-line "dim item = task.selection[i]" writeToVBCode)
(write-line "if (((item.CID = 53 or item.CID = 54) and item.dim[2].value <= 12) or ((item.CID = 807 or item.CID = 812) and item.dim[1].value <= 12)) then" writeToVBCode)
(write-line "if item.CID = 53 or item.CID = 54 then" writeToVBCode)
(write-line "item.dim[5].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.damper[4].value = \"KS7L-l\"" writeToVBCode)
(write-line "item.damper[4].locked = true" writeToVBCode)
(write-line "item.update()" writeToVBCode)
(write-line "elseif item.CID = 807 or item.CID = 812 then" writeToVBCode)
(write-line "item.dim[4].value = 6" writeToVBCode)
(write-line "item.damper[2].value = \"KS7L-l\"" writeToVBCode)
(write-line "item.damper[2].locked = true" writeToVBCode)
(write-line "item.damper[3].value = \"KS7L-l\"" writeToVBCode)
(write-line "item.damper[3].locked = true" writeToVBCode)
(write-line "item.damper[4].value = \"KS7L-l\"" writeToVBCode)
(write-line "item.damper[4].locked = true" writeToVBCode)
(write-line "item.update()" writeToVBCode)
(write-line "end if" writeToVBCode)
(write-line "elseif (((item.CID = 53 or item.CID = 54) and item.dim[2].value > 12) or ((item.CID = 807 or item.CID = 812) and item.dim[1].value > 12)) then" writeToVBCode)
(write-line "if item.CID = 53 or item.CID = 54 then" writeToVBCode)
(write-line "item.dim[5].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.damper[4].value = \"3/8\"+qt+\" ROD-L\"" writeToVBCode)
(write-line "item.damper[4].locked = true" writeToVBCode)
(write-line "item.update()" writeToVBCode)
(write-line "elseif item.CID = 807 or item.CID = 812 then" writeToVBCode)
(write-line "item.dim[4].value = 6" writeToVBCode)
(write-line "item.damper[2].value = \"3/8\"+qt+\" ROD-L\"" writeToVBCode)
(write-line "item.damper[2].locked = true" writeToVBCode)
(write-line "item.damper[3].value = \"3/8\"+qt+\" ROD-L\"" writeToVBCode)
(write-line "item.damper[3].locked = true" writeToVBCode)
(write-line "item.damper[4].value = \"3/8\"+qt+\" ROD-L\"" writeToVBCode)
(write-line "item.damper[4].locked = true" writeToVBCode)
(write-line "item.update()" writeToVBCode)
(write-line "end if" writeToVBCode)
(write-line "item.update()" writeToVBCode)
(write-line "end if" writeToVBCode)
(write-line "end function" writeToVBCode)
(write-line "function turnOffD2D3D4 ()" writeToVBCode)
(write-line "dim item = task.selection[i]" writeToVBCode)
(write-line "if item.CID = 53 or item.CID = 54 then" writeToVBCode)
(write-line "item.dim[5].value = 0" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.damper[4].value = \"NONE\"" writeToVBCode)
(write-line "item.damper[4].locked = true" writeToVBCode)
(write-line "item.update()" writeToVBCode)
(write-line "elseif item.CID = 807 or item.CID = 812 then" writeToVBCode)
(write-line "item.dim[4].value = 1" writeToVBCode)
(write-line "item.damper[2].value = \"NONE\"" writeToVBCode)
(write-line "item.damper[2].locked = true" writeToVBCode)
(write-line "item.damper[3].value = \"NONE\"" writeToVBCode)
(write-line "item.damper[3].locked = true" writeToVBCode)
(write-line "item.damper[4].value = \"NONE\"" writeToVBCode)
(write-line "item.damper[4].locked = true" writeToVBCode)
(write-line "item.update()" writeToVBCode)
(write-line "end if" writeToVBCode)
(write-line "end function" writeToVBCode)
(write-line "rem~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~~" writeToVBCode)
(write-line "if item.CID = 51 or item.CID = 751 or item.CID = 875 or item.CID = 345 or item.CID = 16 or item.CID = 8 then" writeToVBCode)
(write-line "if item.dampers = 1 then" writeToVBCode)
(write-line "if ((item.CID = 345 or item.CID = 16 or item.CID = 8) and item.damper[1].value = \"NONE\") then" writeToVBCode)
(write-line "turnOnTapSqRdDamper ()" writeToVBCode)
(write-line "elseif ((item.CID = 345 or item.CID = 16 or item.CID = 8) and item.damper[1].value <> \"NONE\") then" writeToVBCode)
(write-line "turnOffTapSqRdDamper ()" writeToVBCode)
(write-line "end if" writeToVBCode)
(write-line "elseif item.dampers = 2 then" writeToVBCode)
(write-line "if item.CID = 51 and item.damper[2].value = \"NONE\" then" writeToVBCode)
(write-line "turnOnTapSqRdDamper ()" writeToVBCode)
(write-line "elseif item.CID = 51 and item.damper[2].value <> \"NONE\" then" writeToVBCode)
(write-line "turnOffTapSqRdDamper ()" writeToVBCode)
(write-line "end if" writeToVBCode)
(write-line "elseif item.dampers = 3 then" writeToVBCode)
(write-line "if ((item.CID = 751 or item.CID = 875) and item.damper[3].value = \"NONE\") then" writeToVBCode)
(write-line "turnOnTapSqRdDamper ()" writeToVBCode)
(write-line "elseif ((item.CID = 751 or item.CID = 875) and item.damper[3].value <> \"NONE\") then" writeToVBCode)
(write-line "turnOffTapSqRdDamper ()" writeToVBCode)
(write-line "end if" writeToVBCode)
(write-line "end if" writeToVBCode)
(write-line "elseif item.CID <> 51 and item.CID <> 751 and item.CID <> 875 and item.CID <> 345 and item.CID <> 16 and item.CID <> 8 then" writeToVBCode)
(write-line "if item.dampers = 1 then" writeToVBCode)
(write-line "if item.damper[1].value = \"NONE\" then" writeToVBCode)
(write-line "turnOnD1 ()" writeToVBCode)
(write-line "elseif item.damper[1].value <> \"NONE\" then" writeToVBCode)
(write-line "turnOffD1 ()" writeToVBCode)
(write-line "end if" writeToVBCode)
(write-line "elseif item.dampers = 2 then" writeToVBCode)
(write-line "if item.damper[2].value = \"NONE\" then" writeToVBCode)
(write-line "turnOnD2 ()" writeToVBCode)
(write-line "elseif item.damper[2].value <> \"NONE\" then" writeToVBCode)
(write-line "turnOffD2 ()" writeToVBCode)
(write-line "end if" writeToVBCode)
(write-line "elseif item.dampers = 3 then" writeToVBCode)
(write-line "if item.damper[2].value = \"NONE\" and item.damper[3].value = \"NONE\" then" writeToVBCode)
(write-line "turnOnD3 ()" writeToVBCode)
(write-line "elseif item.damper[2].value = \"NONE\" and item.damper[3].value <> \"NONE\" then" writeToVBCode)
(write-line "turnOffD3 ()" writeToVBCode)
(write-line "turnOnD2 ()" writeToVBCode)
(write-line "elseif item.damper[2].value <> \"NONE\" and item.damper[3].value = \"NONE\" then" writeToVBCode)
(write-line "turnOnD2D3 ()" writeToVBCode)
(write-line "elseif item.damper[2].value <> \"NONE\" and item.damper[3].value <> \"NONE\" then" writeToVBCode)
(write-line "turnOffD2D3 ()" writeToVBCode)
(write-line "end if" writeToVBCode)
(write-line "elseif item.dampers = 4 then" writeToVBCode)
(write-line "if item.damper[2].value = \"NONE\" and item.damper[3].value = \"NONE\" and item.damper[4].value = \"NONE\" then" writeToVBCode)
(write-line "turnOnD3 ()" writeToVBCode)
(write-line "elseif item.damper[2].value = \"NONE\" and item.damper[3].value <> \"NONE\" and item.damper[4].value = \"NONE\" then" writeToVBCode)
(write-line "turnOffD3 ()" writeToVBCode)
(write-line "turnOnD4 ()" writeToVBCode)
(write-line "elseif item.damper[2].value = \"NONE\" and item.damper[3].value = \"NONE\" and item.damper[4].value <> \"NONE\" then" writeToVBCode)
(write-line "turnOffD4 ()" writeToVBCode)
(write-line "turnOnD2 ()" writeToVBCode)
(write-line "elseif item.damper[2].value <> \"NONE\" and item.damper[3].value = \"NONE\" and item.damper[4].value = \"NONE\" then" writeToVBCode)
(write-line "turnOnD3 ()" writeToVBCode)
(write-line "elseif item.damper[2].value <> \"NONE\" and item.damper[3].value <> \"NONE\" and item.damper[4].value = \"NONE\" then" writeToVBCode)
(write-line "turnOffD3 ()" writeToVBCode)
(write-line "turnOnD4 ()" writeToVBCode)
(write-line "elseif item.damper[2].value <> \"NONE\" and item.damper[3].value = \"NONE\" and item.damper[4].value <> \"NONE\" then" writeToVBCode)
(write-line "turnOffD2 ()" writeToVBCode)
(write-line "turnOnD3 ()" writeToVBCode)
(write-line "elseif item.damper[2].value = \"NONE\" and item.damper[3].value <> \"NONE\" and item.damper[4].value <> \"NONE\" then" writeToVBCode)
(write-line "turnOnD2 ()" writeToVBCode)
(write-line "elseif item.damper[2].value <> \"NONE\" and item.damper[3].value <> \"NONE\" and item.damper[4].value <> \"NONE\" then" writeToVBCode)
(write-line "turnOffD2D3D4 ()" writeToVBCode)
(write-line "end if" writeToVBCode)
(write-line "end if" writeToVBCode)
(write-line "end if" writeToVBCode)
(write-line "i = i + 1" writeToVBCode)
(write-line "end while" writeToVBCode)
  (close writeToVBCode)
  (Executescript vbCode)
  (vl-file-delete vbCode)
  (prompt "Cycling through volume damper locations...")(princ)
  (princ)
(END_ROUTINE));end defun
