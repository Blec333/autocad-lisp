;|
APPLOAD DEPENDENCIES TO INCLUDE

  UTILITIES:
    utilityFunctions.lsp

  COMMANDS:
    
|;

(defun c:Set_Layer_Filters ()
  (vl-load-com)
  (setvar 'cmdecho 0)
    (progn
      (vl-catch-all-apply
        (function
          (lambda ()
            (vlax-for element(vla-Item(vla-GetExtensionDictionary(vla-get-Layers(vla-get-ActiveDocument(vlax-get-acad-object))))"ACAD_LAYERFILTERS")
              (vla-Delete element)
            (vlax-for element (vla-Item(vla-GetExtensionDictionary(vla-get-Layers(vla-get-ActiveDocument(vlax-get-acad-object))))"AcLyDictionary")
              (vla-Delete element)
            )
          );for
        );lamb
      );func
    );catch
  );progn
  (Command "-layer" "filter" "_N" "_P" "All" "NAME==\"~*|*\"" "" "01.) Non-XREF (Native)" "")
  
  (Command "-layer" "filter" "_N" "_P" "All" "NAME==\"*|*\"" "" "02.) XREF Only" "")
  (Command "-layer" "filter" "_N" "_P" "02.) XREF Only" "NAME==\"*|M-HVAC-*-NUMB-*\" or NAME==\"*|M-HVAC-*-SIZE-*\" or NAME==\"*|M-HVAC-*-ALIA-*\" or NAME==\"*|M-HVAC-*-LEVE-*\" or NAME==\"*|M-HVAC-*-DIMN-*\" or NAME==\"*|M-HVAC-*-OSET-*\" or NAME==\"*TEXT*\" or NAME==\"*GTXT*\"" "" "Xref Text" "")
  (Command "-layer" "filter" "_N" "_P" "Xref Text" "NAME==\"*|M-HVAC-*-NUMB-*\" or NAME==\"*|M-HVAC-*-SIZE-*\" or NAME==\"*|M-HVAC-*-ALIA-*\" or NAME==\"*|M-HVAC-*-LEVE-*\" or NAME==\"*|M-HVAC-*-DIMN-*\" or NAME==\"*|M-HVAC-*-OSET-*\"" "" "All CADmep Text" "")
  (Command "-layer" "filter" "_N" "_P" "Xref Text" "NAME==\"*|M-HVAC-*-SIZE-*\" or NAME==\"*|M-HVAC-*-ALIA-*\" or NAME==\"*|M-HVAC-*-LEVE-*\" or NAME==\"*|M-HVAC-*-DIMN-*\" or NAME==\"*|M-HVAC-*-OSET-*\"" "" "Numbers Excluded" "")
  (Command "-layer" "filter" "_N" "_P" "Xref Text" "NAME==\"*|M-HVAC-*-ALIA-*\"" "" "Aliases" "")
  (Command "-layer" "filter" "_N" "_P" "Xref Text" "NAME==\"*|M-HVAC-*-LEVE-*\"" "" "Elevations" "")
  (Command "-layer" "filter" "_N" "_P" "Xref Text" "NAME==\"*|M-HVAC-*-DIMN-*\"" "" "Lengths" "")
  (Command "-layer" "filter" "_N" "_P" "Xref Text" "NAME==\"*|M-HVAC-*-NUMB-*\"" "" "Numbers" "")
  (Command "-layer" "filter" "_N" "_P" "Xref Text" "NAME==\"*|M-HVAC-*-OSET-*\"" "" "Offsets" "")
  (Command "-layer" "filter" "_N" "_P" "Xref Text" "NAME==\"*|M-HVAC-*-SIZE-*\"" "" "Sizes" "")
  (Command "-layer" "filter" "_N" "_P" "Xref Text" "NAME==\"*GTXT*\" or NAME==\"*TEXT*\"" "" "Drawing Text" "")
  
  (Command "-layer" "filter" "_N" "_P" "All" "NAME==\"#-XREF-*\"" "" "03.) Xref Attachment" "")
  (Command "-layer" "filter" "_N" "_P" "All" "NAME==\"M-AMC-BKGD-*\"" "" "04.) Background" "")
  (Command "-layer" "filter" "_N" "_P" "All" "FROZEN==\"FALSE\"" "" "05.) Thawed" "")
  (Command "-layer" "filter" "_N" "_P" "05.) Thawed" "NAME==\"*|*\"" "" "Xref Thawed" "")
  (Command "-layer" "filter" "_N" "_P" "05.) Thawed" "NAME==\"~*|*\"" "" "DWG Thawed" "")
  (Command "-layer" "filter" "_N" "_P" "All" "FROZEN==\"TRUE\"" "" "06.) Frozen" "")
  (Command "-layer" "filter" "_N" "_P" "06.) Frozen" "NAME==\"*|*\"" "" "Xref Frozen" "")
  (Command "-layer" "filter" "_N" "_P" "06.) Frozen" "NAME==\"~*|*\"" "" "DWG Frozen" "")
  (Command "-layer" "filter" "_N" "_P" "All" "LOCKED==\"FALSE\"" "" "07.) Unlocked" "")
  (Command "-layer" "filter" "_N" "_P" "07.) Unlocked" "NAME==\"*|*\"" "" "Xref Unlocked" "")
  (Command "-layer" "filter" "_N" "_P" "07.) Unlocked" "NAME==\"~*|*\"" "" "DWG Unlocked" "")
  (Command "-layer" "filter" "_N" "_P" "All" "LOCKED==\"TRUE\"" "" "08.) Locked" "")
  (Command "-layer" "filter" "_N" "_P" "08.) Locked" "NAME==\"*|*\"" "" "Xref Locked" "")
  (Command "-layer" "filter" "_N" "_P" "08.) Locked" "NAME==\"~*|*\"" "" "DWG Locked" "")
  (Command "-layer" "filter" "_N" "_P" "All" "OFF==\"FALSE\"" "" "09.) On" "")
  (Command "-layer" "filter" "_N" "_P" "09.) On" "NAME==\"*|*\"" "" "Xref On" "")
  (Command "-layer" "filter" "_N" "_P" "09.) On" "NAME==\"~*|*\"" "" "DWG On" "")
  (Command "-layer" "filter" "_N" "_P" "All" "OFF==\"TRUE\"" "" "10.) Off" "")
  (Command "-layer" "filter" "_N" "_P" "10.) Off" "NAME==\"*|*\"" "" "Xref Off" "")
  (Command "-layer" "filter" "_N" "_P" "10.) Off" "NAME==\"~*|*\"" "" "DWG Off" "")
  (Command "-layer" "filter" "_N" "_P" "All" "PLOTTABLE==\"TRUE\"" "" "11.) Plottable" "")
  (Command "-layer" "filter" "_N" "_P" "11.) Plottable" "NAME==\"*|*\"" "" "Xref Off" "")
  (Command "-layer" "filter" "_N" "_P" "11.) Plottable" "NAME==\"~*|*\"" "" "DWG Off" "")
  (Command "-layer" "filter" "_N" "_P" "All" "PLOTTABLE==\"FALSE\"" "" "12.) Not Plottable" "")
  (Command "-layer" "filter" "_N" "_P" "12.) Not Plottable" "NAME==\"*|*\"" "" "Xref Off" "")
  (Command "-layer" "filter" "_N" "_P" "12.) Not Plottable" "NAME==\"~*|*\"" "" "DWG Off" "")

  (Command "-layer" "filter" "_N" "_P" "All" "NAME==\"*|*\"" "" "BACKGROUND" "")
  (Command "-layer" "filter" "_N" "_P" "BACKGROUND" "NAME==\"A-*\" or NAME==\"*ARCH*\"" "" "Arch" "")
  (Command "-layer" "filter" "_N" "_P" "BACKGROUND" "NAME==\"*Floorplan*\" or NAME==\"*Floor plan*\"" "" "Floorplan" "")
  (Command "-layer" "filter" "_N" "_P" "BACKGROUND" "NAME==\"*ReflectedCeilingPlan*\" or NAME==\"*Reflected Ceiling Plan*\" or NAME==\"*RCP*\"" "" "Floorplan" "")
  (Command "-layer" "filter" "_N" "_P" "BACKGROUND" "NAME==\"P-*\"" "" "Plumbing" "")
  (Command "-layer" "filter" "_N" "_P" "BACKGROUND" "NAME==\"S-*\"" "" "Struct" "")
  (Command "-layer" "filter" "_N" "_P" "BACKGROUND" "NAME==\"M-*\"" "" "HVAC" "")
  (Command "-layer" "filter" "_N" "_P" "BACKGROUND" "NAME==\"E-*\"" "" "Electrical" "")
  (Command "-layer" "filter" "_N" "_P" "BACKGROUND" "NAME==\"*GRID*\"" "" "Grid" "")
  (Command "-layer" "filter" "_N" "_P" "BACKGROUND" "NAME==\"*COLS*\"" "" "Cols" "")
  (Command "-layer" "filter" "_N" "_P" "BACKGROUND" "NAME==\"*DOOR*\"" "" "Doors" "")
  (Command "-layer" "filter" "_N" "_P" "BACKGROUND" "NAME==\"*GLAZ*\"" "" "Windows" "")
  (Command "-layer" "filter" "_N" "_P" "BACKGROUND" "NAME==\"*HRAL*\"" "" "Railing" "")
  (Command "-layer" "filter" "_N" "_P" "BACKGROUND" "NAME==\"*PAT*\"" "" "Patterns" "")
  (Command "-layer" "filter" "_N" "_P" "BACKGROUND" "NAME==\"*FURN*\"" "" "Furniture" "")
  (Command "-layer" "filter" "_N" "_P" "BACKGROUND" "NAME==\"*PAT*\"" "" "Patterns" "")
  (Command "-layer" "filter" "_N" "_P" "BACKGROUND" "NAME==\"*A-ANNO*\"" "" "Annotations" "")
  (Command "-layer" "filter" "_N" "_P" "BACKGROUND" "NAME==\"*DIM*\"" "" "Dimensions" "")

  (Command "-layer" "filter" "_N" "_P" "All" "NAME==\"*M-HVAC-*\"" "" "SERVICES" "")
  (Command "-layer" "filter" "_N" "_P" "SERVICES" "NAME==\"M-HVAC-CA*\"" "" "Combustion Air" "")
  (Command "-layer" "filter" "_N" "_P" "Combustion Air" "NAME==\"*|*\"" "" "Xref Combustion Air" "")
  (Command "-layer" "filter" "_N" "_P" "Combustion Air" "NAME==\"~*|*\"" "" "DWG Combustion Air" "")
  (Command "-layer" "filter" "_N" "_P" "SERVICES" "NAME==\"M-HVAC-EL*\"" "" "Exhaust Low Pressure" "")
  (Command "-layer" "filter" "_N" "_P" "Exhaust Low Pressure" "NAME==\"*|*\"" "" "Xref Exhaust Low Pressure" "")
  (Command "-layer" "filter" "_N" "_P" "Exhaust Low Pressure" "NAME==\"~*|*\"" "" "DWG Exhaust Low Pressure" "")
  (Command "-layer" "filter" "_N" "_P" "SERVICES" "NAME==\"M-HVAC-EM*\"" "" "Exhaust Medium Pressure" "")
  (Command "-layer" "filter" "_N" "_P" "Exhaust Medium Pressure" "NAME==\"*|*\"" "" "Xref Exhaust Medium Pressure" "")
  (Command "-layer" "filter" "_N" "_P" "Exhaust Medium Pressure" "NAME==\"~*|*\"" "" "DWG Exhaust Medium Pressure" "")
  (Command "-layer" "filter" "_N" "_P" "SERVICES" "NAME==\"M-HVAC-EH*\"" "" "Exhaust High Pressure" "")
  (Command "-layer" "filter" "_N" "_P" "Exhaust High Pressure" "NAME==\"*|*\"" "" "Xref Exhaust High Pressure" "")
  (Command "-layer" "filter" "_N" "_P" "Exhaust High Pressure" "NAME==\"~*|*\"" "" "DWG Exhaust High Pressure" "")
  (Command "-layer" "filter" "_N" "_P" "SERVICES" "NAME==\"M-HVAC-EW*\"" "" "Exhaust Welded" "")
  (Command "-layer" "filter" "_N" "_P" "Exhaust Welded" "NAME==\"*|*\"" "" "Xref Exhaust Welded" "")
  (Command "-layer" "filter" "_N" "_P" "Exhaust Welded" "NAME==\"~*|*\"" "" "DWG Exhaust Welded" "")
  (Command "-layer" "filter" "_N" "_P" "SERVICES" "NAME==\"M-HVAC-EP*\"" "" "Exhaust Air PVC" "")
  (Command "-layer" "filter" "_N" "_P" "Exhaust Air PVC" "NAME==\"*|*\"" "" "Xref Exhaust Air PVC" "")
  (Command "-layer" "filter" "_N" "_P" "Exhaust Air PVC" "NAME==\"~*|*\"" "" "DWG Exhaust Air PVC" "")
  (Command "-layer" "filter" "_N" "_P" "SERVICES" "NAME==\"M-HVAC-EI*\"" "" "Exhaust Air Inslab" "")
  (Command "-layer" "filter" "_N" "_P" "Exhaust Air Inslab" "NAME==\"*|*\"" "" "Xref Exhaust Air Inslab" "")
  (Command "-layer" "filter" "_N" "_P" "Exhaust Air Inslab" "NAME==\"~*|*\"" "" "DWG Exhaust Air Inslab" "")
  (Command "-layer" "filter" "_N" "_P" "SERVICES" "NAME==\"M-HVAC-OA*\"" "" "Outside Air" "")
  (Command "-layer" "filter" "_N" "_P" "Outside Air" "NAME==\"*|*\"" "" "Xref Outside Air" "")
  (Command "-layer" "filter" "_N" "_P" "Outside Air" "NAME==\"~*|*\"" "" "DWG Outside Air" "")
  (Command "-layer" "filter" "_N" "_P" "SERVICES" "NAME==\"M-HVAC-RL*\"" "" "Return Low Pressure" "")
  (Command "-layer" "filter" "_N" "_P" "Return Low Pressure" "NAME==\"*|*\"" "" "Xref Return Low Pressure" "")
  (Command "-layer" "filter" "_N" "_P" "Return Low Pressure" "NAME==\"~*|*\"" "" "DWG Return Low Pressure" "")
  (Command "-layer" "filter" "_N" "_P" "SERVICES" "NAME==\"M-HVAC-RM*\"" "" "Return Medium Pressure" "")
  (Command "-layer" "filter" "_N" "_P" "Return Medium Pressure" "NAME==\"*|*\"" "" "Xref Return Medium Pressure" "")
  (Command "-layer" "filter" "_N" "_P" "Return Medium Pressure" "NAME==\"~*|*\"" "" "DWG Return Medium Pressure" "")
  (Command "-layer" "filter" "_N" "_P" "SERVICES" "NAME==\"M-HVAC-RH*\"" "" "Return High Pressure" "")
  (Command "-layer" "filter" "_N" "_P" "Return High Pressure" "NAME==\"*|*\"" "" "Xref Return High Pressure" "")
  (Command "-layer" "filter" "_N" "_P" "Return High Pressure" "NAME==\"~*|*\"" "" "DWG Return High Pressure" "")
  (Command "-layer" "filter" "_N" "_P" "SERVICES" "NAME==\"M-HVAC-SL*\"" "" "Supply Low Pressure" "")
  (Command "-layer" "filter" "_N" "_P" "Supply Low Pressure" "NAME==\"*|*\"" "" "Xref Supply Low Pressure" "")
  (Command "-layer" "filter" "_N" "_P" "Supply Low Pressure" "NAME==\"~*|*\"" "" "DWG Supply Low Pressure" "")
  (Command "-layer" "filter" "_N" "_P" "SERVICES" "NAME==\"M-HVAC-SM*\"" "" "Supply Medium Pressure" "")
  (Command "-layer" "filter" "_N" "_P" "Supply Medium Pressure" "NAME==\"*|*\"" "" "Xref Supply Medium Pressure" "")
  (Command "-layer" "filter" "_N" "_P" "Supply Medium Pressure" "NAME==\"~*|*\"" "" "DWG Supply Medium Pressure" "")
  (Command "-layer" "filter" "_N" "_P" "SERVICES" "NAME==\"M-HVAC-SU*\"" "" "Supply High Pressure" "")
  (Command "-layer" "filter" "_N" "_P" "Supply High Pressure" "NAME==\"*|*\"" "" "Xref Supply High Pressure" "")
  (Command "-layer" "filter" "_N" "_P" "Supply High Pressure" "NAME==\"~*|*\"" "" "DWG Supply High Pressure" "")
  (Command "-layer" "filter" "_N" "_P" "SERVICES" "NAME==\"M-HVAC-SH*\"" "" "Supply Underground" "")
  (Command "-layer" "filter" "_N" "_P" "Supply Underground" "NAME==\"*|*\"" "" "Xref Supply Underground" "")
  (Command "-layer" "filter" "_N" "_P" "Supply Underground" "NAME==\"~*|*\"" "" "DWG Supply Underground" "")
  (Command "-layer" "filter" "_N" "_P" "SERVICES" "NAME==\"M-HVAC-TA*\"" "" "Transfer Air" "")
  (Command "-layer" "filter" "_N" "_P" "Transfer Air" "NAME==\"*|*\"" "" "Xref Transfer Air" "")
  (Command "-layer" "filter" "_N" "_P" "Transfer Air" "NAME==\"~*|*\"" "" "DWG Transfer Air" "")
  (Command "-layer" "filter" "_N" "_P" "SERVICES" "NAME==\"M-HVAC-TS*\"" "" "Trimble Seismic" "")
  (Command "-layer" "filter" "_N" "_P" "Trimble Seismic" "NAME==\"*|*\"" "" "Xref Trimble Seismic" "")
  (Command "-layer" "filter" "_N" "_P" "Trimble Seismic" "NAME==\"~*|*\"" "" "DWG Trimble Seismic" "")

  (Command "-layer" "filter" "_N" "_P" "All" "NAME==\"M-HVAC-*-A\" or NAME==\"M-HVAC-*-D\" or NAME==\"M-HVAC-*-I\" or NAME==\"M-HVAC-*-R\" or NAME==\"M-HVAC-*-EXST\"" "" "STATUS" "")
  (Command "-layer" "filter" "_N" "_P" "STATUS" "NAME==\"M-HVAC-*-A\"" "" "Approved" "")
  (Command "-layer" "filter" "_N" "_P" "STATUS" "NAME==\"M-HVAC-*-D\"" "" "Design" "")
  (Command "-layer" "filter" "_N" "_P" "STATUS" "NAME==\"M-HVAC-*-I\"" "" "Issued" "")
  (Command "-layer" "filter" "_N" "_P" "STATUS" "NAME==\"M-HVAC-*-R\"" "" "Revised" "")
  (Command "-layer" "filter" "_N" "_P" "STATUS" "NAME==\"M-HVAC-*-EXST\"" "" "Existing" "")

  (Command "-layer" "filter" "_N" "_P" "All" "NAME==\"M-HVAC-*-NUMB-*\" or NAME==\"M-HVAC-*-SIZE-*\" or NAME==\"M-HVAC-*-ALIA-*\" or NAME==\"M-HVAC-*-LEVE-*\" or NAME==\"M-HVAC-*-DIMN-*\" or NAME==\"M-HVAC-*-OSET-*\" or NAME==\"*TEXT*\" or NAME==\"*GTXT*\"" "" "TEXT" "")
  (Command "-layer" "filter" "_N" "_P" "TEXT" "NAME==\"M-HVAC-*-NUMB-*\" or NAME==\"M-HVAC-*-SIZE-*\" or NAME==\"M-HVAC-*-ALIA-*\" or NAME==\"M-HVAC-*-LEVE-*\" or NAME==\"M-HVAC-*-DIMN-*\" or NAME==\"M-HVAC-*-OSET-*\"" "" "All CADmep Text" "")
  (Command "-layer" "filter" "_N" "_P" "TEXT" "NAME==\"M-HVAC-*-SIZE-*\" or NAME==\"M-HVAC-*-ALIA-*\" or NAME==\"M-HVAC-*-LEVE-*\" or NAME==\"M-HVAC-*-DIMN-*\" or NAME==\"M-HVAC-*-OSET-*\"" "" "Numbers Excluded" "")
  (Command "-layer" "filter" "_N" "_P" "TEXT" "NAME==\"M-HVAC-*-ALIA-*\"" "" "Aliases" "")
  (Command "-layer" "filter" "_N" "_P" "TEXT" "NAME==\"M-HVAC-*-LEVE-*\"" "" "Elevations" "")
  (Command "-layer" "filter" "_N" "_P" "TEXT" "NAME==\"M-HVAC-*-DIMN-*\"" "" "Lengths" "")
  (Command "-layer" "filter" "_N" "_P" "TEXT" "NAME==\"M-HVAC-*-NUMB-*\"" "" "Numbers" "")
  (Command "-layer" "filter" "_N" "_P" "TEXT" "NAME==\"M-HVAC-*-OSET-*\"" "" "Offsets" "")
  (Command "-layer" "filter" "_N" "_P" "TEXT" "NAME==\"M-HVAC-*-SIZE-*\"" "" "Sizes" "")
  (Command "-layer" "filter" "_N" "_P" "TEXT" "NAME==\"*GTXT*\" or NAME==\"*TEXT*\"" "" "Drawing Text" "")

  (Command "-layer" "filter" "_N" "_P" "All" "NAME==\"*GDIM*\"" "" "Drawing Dimensions" "")
  (Command "-layer" "filter" "_N" "_P" "All" "NAME==\"M-HVAC-*-ISRT-*\"" "" "Trimble Points" "")
  (Command "-layer" "filter" "_N" "_P" "All" "NAME==\"M-HVAC-*-BKOT-*\"" "" "Blockouts" "")
  (Command "-layer" "filter" "_N" "_P" "All" "NAME==\"M-HVAC-*HG-*\"" "" "Hangers" "")
  (Command "-layer" "filter" "_N" "_P" "All" "NAME==\"M-AMC-TAGS-*\"" "" "Tags" "")
  (Command "-layer" "filter" "_N" "_P" "All" "NAME==\"M-HVAC-*FS-*\"" "" "Floor Support" "")
  (Command "-layer" "filter" "_N" "_P" "All" "NAME==\"M-HVAC-*-HIDE-*\"" "" "Hidden Lines" "")
  (Command "-layer" "filter" "_N" "_P" "All" "NAME==\"M-AMC-*-KYPL-*\"" "" "Keyplan Layers" "")
  (princ)
);end defun
